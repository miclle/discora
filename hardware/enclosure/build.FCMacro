"""Build the editable Discora V4 top-loading concept in FreeCAD. Units: mm."""
import os
import math
import sys
from pathlib import Path

import FreeCAD as A
import FreeCADGui as G
import Part
import Sketcher
from PySide import QtCore, QtWidgets

sys.path.insert(0, str(Path(__file__).resolve().parent))
import perfboard_geometry as perfboard
import speaker_wire_geometry as speaker_wires
import speaker_print_geometry as speaker_print
import speaker_duct_geometry as speaker_duct

V = A.Vector
X, Y, Z = V(1, 0, 0), V(0, 1, 0), V(0, 0, 1)
# P1: Bambu PLA Lite Orange 16301, #FF671F (Bambu Studio filament color table).
ORANGE, TEAL, BLACK, RUBBER = (1.0, 0.403921568627451, 0.12156862745098039), (0.025, 0.75, 0.72), (0.145, 0.155, 0.17), (0.07, 0.08, 0.09)
GLASS, PIXEL = (0.045, 0.085, 0.10), (0.85, 0.97, 1.0)
# Knob: Bambu PLA Basic Black 10101; white is the PLA Lite symbol region.
KNOB_BLACK, WHITE, SILVER, PCB, BLUE = (0.0, 0.0, 0.0), (1.0, 1.0, 1.0), (0.70, 0.73, 0.75), (0.14, 0.40, 0.32), (0.12, 0.33, 0.62)
# The drive face is parallel to XZ and the disc moves vertically behind the handle.
WIDTH = 170.0
DRIVE = (128.0, 10.8, 130.0)  # measured maximum envelope; front lip is thicker than the 9.5 mm rear
# The flange keeps the original nominal outside width/height as an envelope.
SPEAKER_FLANGE = (45.0, 80.0)
SPEAKER_BASKET = (38.3, 70.5)  # width, height of the measured maximum section
SPEAKER_FRONT_DEPTH, SPEAKER_REAR_DEPTH = 2.0, 39.0
SPEAKER_SEAT_Y = 10.0
SPEAKER_CORNER_RADIUS = 12.0  # trial radius; the basket outline is unmeasured
SPEAKER_FIT_CLEARANCE = 0.5  # per side at the straight edges
SPEAKER_HOLE_PITCH = (36.0, 70.0)
SPEAKER_HOLE_DIAMETER = 3.3
SPEAKER_PILOT_DIAMETER, SPEAKER_PILOT_DEPTH = 2.3, 10.5
CASE_DEPTH = 93.0
# The rear housing is symmetric in side elevation; the front skin overlays it.
HANDLE_THICKNESS = 5.0
FRONT_THICKNESS = HANDLE_THICKNESS
REAR_THICKNESS = FRONT_THICKNESS
INNER_HALF_WIDTH = WIDTH/2-REAR_THICKNESS
LOWER_FASTENER_X = WIDTH/2-5.6
LOWER_FASTENER_Z = 33.0
# Keep the existing floor plane Z=6 and the 3 mm soft-foot height.
BASE_Z = 1.0
FEET_BOTTOM_Z = BASE_Z - 3.0
# Move internal hardware back by the added front wall thickness.
INTERNAL_SHIFT_Y = FRONT_THICKNESS - 3.0
SHOULDER_RUN = (CASE_DEPTH - HANDLE_THICKNESS) / 2
SHOULDER_SLOPE = 27.0 / 38.0
EAVE_Z = 165.0
SHOULDER_Z = EAVE_Z + SHOULDER_RUN * SHOULDER_SLOPE
HANDLE_FRONT, HANDLE_REAR = SHOULDER_RUN, CASE_DEPTH - SHOULDER_RUN
HANDLE_HEIGHT = 45.0
HANDLE_OPENING_HEIGHT = 24.0
HANDLE_TOP = SHOULDER_Z + HANDLE_HEIGHT
OUTER_CORNER_RADIUS = 4.0
ROOF_OFFSET_Z = REAR_THICKNESS * math.sqrt(1 + SHOULDER_SLOPE**2)
FRONT_OFFSET_Z = FRONT_THICKNESS * math.sqrt(1 + SHOULDER_SLOPE**2)
REAR_CENTER_Y = (FRONT_THICKNESS + CASE_DEPTH) / 2
REAR_EAVE_Z = EAVE_Z + FRONT_THICKNESS*SHOULDER_SLOPE - FRONT_OFFSET_Z
REAR_SHOULDER_Z = REAR_EAVE_Z + (CASE_DEPTH-REAR_CENTER_Y)*SHOULDER_SLOPE
INNER_CENTER_Y = CASE_DEPTH/2 + (REAR_EAVE_Z-EAVE_Z+FRONT_OFFSET_Z-ROOF_OFFSET_Z)/(2*SHOULDER_SLOPE)
INNER_FRONT, INNER_REAR = INNER_CENTER_Y-1.25, INNER_CENTER_Y+1.25
INNER_PEAK_Z = EAVE_Z + INNER_FRONT * SHOULDER_SLOPE - FRONT_OFFSET_Z
FRONT_INNER_EAVE_Z = EAVE_Z + FRONT_THICKNESS * SHOULDER_SLOPE - FRONT_OFFSET_Z
INNER_EAVE_Z = REAR_EAVE_Z + REAR_THICKNESS * SHOULDER_SLOPE - ROOF_OFFSET_Z
# Two front-facing drivers share one circular grille, but separate rear cavities.
SPEAKER_CENTER_X, SPEAKER_CENTER_Z = 26.0, 76.0
# Independent P3 ducts exit at Z=65; P2 provides a clear, flush rim.
PORT_CENTER_Y, PORT_CENTER_Z = 47.5, speaker_duct.ELBOW_Z
CHAMBER_DEPTH = 52.0 + (CASE_DEPTH - 82.0) / 2
CHAMBER_SIDE_X = INNER_HALF_WIDTH - 0.7
FRONT_GRILLE_RADIUS = 65.0
# A true circular mouth precedes the grille; +Y is inward from the front face.
FRONT_GRILLE_RECESS = 2.5
GRILLE_HOLE_RADIUS, GRILLE_PITCH = .94, 2.9
GRILLE_UNDERLAP = 3.0
# Supplier image: selected flat 5600 mAh pack, excluding leads/connectors.
BATTERY = (112.0, 70.0, 20.0)
# The measured underside faces the rear wall; 1 mm is reserved for protective pads.
DRIVE_DATUM_Y = CASE_DEPTH - REAR_THICKNESS - 1.0
DRIVE_TOP = 159.5
SLOT_Y = DRIVE_DATUM_Y - (5.9 + 10.0) / 2
SLOT_HEIGHT = 5.5  # 4.5 mm reported opening plus 0.5 mm each side
CABLE_SIDE_ALLOWANCE = 14.5  # measured natural cable extent; 1.5 mm side-wall clearance

# OLED supplier drawing: dimensions are nominal, not measured hardware.
# The origin is the active-area center; +Z points toward the four-pin header.
DISPLAY_WINDOW = (30.42, 15.7)  # 0.5 mm beyond the active area on each side
DISPLAY_OUTER_WINDOW = (32.82, 18.1)  # flared mouth; throat starts 0.8 mm inward
DISPLAY_DECK_Y = 18.0
DISPLAY_PCB = (35.4, 1.2, 33.5)
DISPLAY_HOLES = [(x,z) for x in (-15.2,15.2) for z in (-16.3,12.2)]


def bottom_corner_envelope():
    """Match the handle's XZ corner arcs across the full enclosure depth.

    A shared envelope keeps P1/P2 coincident at the seam and preserves the
    rear housing's front/back side-outline symmetry. Only Z=BASE_Z..BASE_Z+4 is trimmed.
    """
    blank = Part.makeBox(WIDTH, CASE_DEPTH, HANDLE_TOP, V(-WIDTH/2, 0, BASE_Z))
    edges = [e for e in blank.Edges
             if abs(e.CenterOfMass.z-BASE_Z) < 1e-7
             and abs(abs(e.CenterOfMass.x)-WIDTH/2) < 1e-7]
    assert len(edges) == 2
    return blank.makeFillet(OUTER_CORNER_RADIUS, edges)


def volume_shapes(grip_tip_diameter=5.6):
    """PCB B50K module; local +Y is inward, +Z up the slope.

    PCB 35 x 26.2 x 1.5; complete thickness including plugged connectors
    and pins is 15. Front PCB edge is flush with the body mounting face.
    Rotate the module 90 degrees about its shaft to clear MCU components.
    Original body, bushing and spline geometry remain nominal assumptions.
    Connector/pin blocks are envelopes, not a measured connector footprint.
    """
    body=Part.makeBox(9.5,14.5,11.2,V(-4.75,3.6,-2.7))
    pcb=Part.makeBox(35,26.2,1.5,V(-17.5,3.6,-4.2))
    connectors=Part.makeBox(35,11.7,11.2,V(-17.5,18.1,-2.7))
    pins=Part.makeBox(35,26.2,2.3,V(-17.5,3.6,-6.5))
    module=Part.makeCompound([body,pcb,connectors,pins])
    module.rotate(V(),Y,90)
    shaft=Part.makeCylinder(3.4,5,V(0,3.6,0),-Y).fuse(
        Part.makeCylinder(2.9,10,V(0,-1.4,0),-Y))
    # Reserve the entire module envelope, with 0.3 mm transverse clearance.
    # Keep the mounting face at 3.6: the recessed nut still clamps a 2 mm web.
    pocket=Part.makeBox(35.6,26.5,15.6,V(-17.8,3.6,-6.8))
    pocket.rotate(V(),Y,90)
    # Exterior recess: 0.4 mm mouth bevel; bottom at 1.6 leaves the web 2 mm.
    recess=Part.makeCylinder(12.8,.2,V(0,-.2,0),Y).fuse(
        Part.makeCone(12.8,12.4,.4,V(),Y)).fuse(
        Part.makeCylinder(12.4,1.2,V(0,.4,0),Y)).removeSplitter()
    radius=9.8/math.sqrt(3)
    vertices=[V(radius*math.cos(i*math.pi/3),1.6,radius*math.sin(i*math.pi/3)) for i in range(6)]
    nut=Part.Face(Part.makePolygon(vertices+vertices[:1])).extrude(-Y*1.9).cut(
        Part.makeCylinder(3.4,1.9,V(0,1.6,0),-Y))
    shaft=shaft.fuse(nut).removeSplitter()
    disk=Part.makeCylinder(12,1.4,V(0,1,0),-Y)
    # Slender full-height lobes: 28 mm span, 6.8 mm arm width, R3.4 ends.
    cross=Part.makeBox(21.2,12.5,6.8,V(-10.6,-12.9,-3.4)).fuse(
        Part.makeBox(6.8,12.5,21.2,V(-3.4,-12.9,-10.6)))
    cross=cross.multiFuse([Part.makeCylinder(3.4,12.5,V(x,-12.9,z),Y)
                          for x,z in ((-10.6,0),(10.6,0),(0,-10.6),(0,10.6))]).removeSplitter()
    inside=[e for e in cross.Edges if e.BoundBox.YLength>12
            and abs(abs(e.CenterOfMass.x)-3.4)<1e-6
            and abs(abs(e.CenterOfMass.z)-3.4)<1e-6]
    cross=cross.makeFillet(.8,inside)
    top=[e for e in cross.Edges if abs(e.BoundBox.YMin+12.9)<1e-6
         and abs(e.BoundBox.YMax+12.9)<1e-6]
    cross=cross.makeFillet(.5,top)
    # Round the arm feet before adding the underside taper.
    bottom=[e for e in cross.Edges if abs(e.BoundBox.YMin+.4)<1e-6
            and abs(e.BoundBox.YMax+.4)<1e-6]
    cross=cross.makeFillet(.25,bottom)
    # Support the extended arms with a 45-degree underside transition.
    ramp=Part.makeCone(11.7,14.01,2.31,V(0,-.4,0),-Y)
    arm_limit=ramp.fuse(Part.makeCylinder(14.01,10.2,V(0,-2.71,0),-Y))
    cross=cross.common(arm_limit).removeSplitter()
    # A short flared root closes the nut cavity between the slimmer arms.
    # At the cavity roof Y=-2.4 its radial wall remains over 0.57 mm.
    hub=Part.makeCone(7.2,6.2,3.2,V(0,-.4,0),-Y)
    knob=disk.multiFuse([cross,hub]).removeSplitter()
    # Nut relief and 6 mm carrier bore; six sacrificial ribs grip the actual
    # splines. These are press-fit ribs, not a fabricated matching spline form.
    knob=knob.cut(Part.makeCylinder(6,3.5,V(0,1.1,0),-Y))
    knob=knob.cut(Part.makeCylinder(3,13,V(0,1.3,0),-Y))
    tip=grip_tip_diameter/2
    profile=[(3.2,-10.2),(tip,-10.2),(tip,-4.2),(3,-3.2),(3.2,-3.2)]
    pts=[V(x,y,-.3) for x,y in profile]
    rib=Part.Face(Part.makePolygon(pts+pts[:1])).extrude(Z*.6)
    ribs=[]
    for angle in range(0,360,60):
        s=rib.copy();s.rotate(V(),Y,angle);ribs.append(s)
    knob=knob.multiFuse(ribs).removeSplitter()
    # Flush white PLA index, 0.6 mm deep; two non-overlapping print volumes.
    mark=Part.makeBox(.7,.6,2.2,V(-.35,-12.9,7.1))
    body_black=knob.cut(mark).removeSplitter()
    knob=Part.makeCompound([body_black,mark])
    return dict(body=module,shaft=shaft,pocket=pocket,recess=recess,knob=knob)


def oled_shapes():
    """Local geometry from oled-module-dimensions-wiring.webp, in mm.

    Panel front is 1.0 behind the exterior; a rear pocket leaves a 0.8 lip.
    Four pegs locate the PCB, and a removable frame bears only on hole lands.
    The side-view 11.3 spans
    panel front to bent-pin tip. Header width/thickness are conservative
    reservations (4 pitches by 1 pitch), not measured housing dimensions.
    """
    pcb=Part.makeBox(*DISPLAY_PCB,V(-17.7,2.4,-18.8))
    pcb=pcb.cut(Part.makeBox(14,2,4.01,V(-7,2,-18.81)))
    for x,z in DISPLAY_HOLES:
        pcb=pcb.cut(Part.makeCylinder(1.5,2,V(x,2,z),Y))
    panel=Part.makeBox(34.5,1.4,23,V(-17.25,1,-13.55))
    header=Part.makeBox(10.16,8.7,2.54,V(-5.08,3.6,11.43))
    left=Part.makeCompound([Part.makeCylinder(2.25,.6,V(-15.2,1.8,z),Y).fuse(
        Part.makeCylinder(1.3,1.6,V(-15.2,2.4,z),Y)) for z in (-16.3,12.2)]+
        [Part.makeCylinder(2.5,2.9,V(-20.5,3.5,-7),Y)])
    pilots=Part.makeCompound([Part.makeCylinder(.8,4.5,V(x,2,-7),Y) for x in (-20.5,20.5)])
    pocket=Part.makeBox(34.9,12,23.4,V(-17.45,.8,-13.75)).fuse(
        Part.makeBox(36,12,34.1,V(-18,2.2,-19.1)))
    # Open-bottom U frame leaves the header, PCB centre and lower notch accessible.
    frame=Part.makeBox(44.5,2,3.5,V(-22.25,6.4,15.7))
    members=[]
    for sign in (-1,1):
        cx=sign*20.5
        members.append(Part.makeBox(3.5,2,34.25,V(cx-1.75,6.4,-18.55)))
        members.append(Part.makeCylinder(3,2,V(cx,6.4,-7),Y))
        for z in (-16.3,12.2):
            x=sign*15.2
            members.append(Part.makeCylinder(2.25,4.8,V(x,3.6,z),Y))
            members.append(Part.makeBox(5.3,2,3.5,V(min(x,cx),6.4,z-1.75)))
    frame=frame.multiFuse(members)
    for x,z in DISPLAY_HOLES:
        frame=frame.cut(Part.makeCylinder(1.6,5,V(x,3.5,z),Y))
    for x in (-20.5,20.5):
        frame=frame.cut(Part.makeCylinder(1.1,2.2,V(x,6.3,-7),Y))
    return pcb.removeSplitter(),panel,header,left,pilots,frame.removeSplitter(),pocket.removeSplitter()
# Centers on the exterior slope; front row then rear row.
BUTTONS = [('PlayPause', '播放／暂停', -63.0, 9.0),
           ('Eject', '退碟', -45.0, 9.0),
           ('Prev', '上一曲', -63.0, 26.0),
           ('Next', '下一曲', -45.0, 26.0)]


def button_retainer(row_offset):
    """Open direct-wire support; switch terminal pairs face local +/-Z.

    Two pads per switch bear away from its central molded details. Continuous
    terminal-side openings avoid inventing an unmeasured four-pin footprint.
    """
    def block(x,y,z,w,d,h):
        return Part.makeBox(w,d,h,V(x,y,z))
    frame=block(-1.5,16.5,-row_offset-1.5,3,2,2*row_offset+3)
    frame=frame.fuse(block(-17,16.5,-2.4,34,2,4.8))
    for rz in (-row_offset,row_offset):
        frame=frame.fuse(block(-15,16.5,rz-1.5,30,2,3))
        for cx in (-9,9):
            for dx in (-3.8,3.8):
                frame=frame.fuse(block(cx+dx-1,12,rz-1.5,2,4.5,3))
    for x in (-14,14):
        frame=frame.cut(Part.makeCylinder(1.1,2.3,V(x,16.4,0),Y))
        frame=frame.cut(Part.makeCone(2.1,1.1,1,V(x,18.5,0),-Y))
    return frame.removeSplitter()


def button_parts(key):
    """Return orange body and white symbol solids in the key-local frame."""
    def box(x,y,z,dx,dy,dz):
        return Part.makeBox(dx,dy,dz,V(x,y,z))
    cap=Part.makeCylinder(5,7.2,V(0,-1.2,0),Y).fuse(Part.makeCylinder(6.4,.8,V(0,5.2,0),Y))
    # A 0.6 mm flush white region is printed with the orange body.
    symbols=[]
    def triangle(points):
        pts=[V(xx,-1.2,zz) for xx,zz in points]
        symbols.append(Part.Face(Part.makePolygon(pts+pts[:1])).extrude(Y*.6))
    if key=='PlayPause':
        triangle([(-2.9,-2),(-2.9,2),(0,0)])
        symbols += [box(.7,-1.2,-2,.8,.6,4),box(2.1,-1.2,-2,.8,.6,4)]
    elif key=='Eject':
        triangle([(-2.7,-.2),(2.7,-.2),(0,2.7)])
        symbols.append(box(-2.7,-1.2,-2.1,5.4,.6,.8))
    else:
        sign=-1 if key=='Prev' else 1
        triangle([(-sign*2,-2),(-sign*2,2),(sign*1.8,0)])
        symbols.append(box(-3 if key=='Prev' else 2.2,-1.2,-2,.8,.6,4))
    marks=Part.makeCompound(symbols)
    body=cap.cut(marks).removeSplitter()
    return body,marks


def build(folder):
    doc = A.newDocument("DiscoraV4Topload")
    doc.Label = "Discora V4 · 三件主要 PLA 结构"
    visible = []

    def group(name, label):
        obj = doc.addObject("App::DocumentObjectGroup", name)
        obj.Label = label
        return obj

    shell = group("Shell", "01 · PLA 外壳")
    ui = group("Controls", "02 · 状态屏和操控件")
    supports = group("Carrier", "03 · PLA 内部支架")
    hardware = group("Hardware", "04 · 硬件占位（待实测）")

    def finish(obj, name, color, parent):
        obj.Label = name
        parent.addObject(obj)
        obj.ViewObject.ShapeColor = color
        obj.ViewObject.DisplayMode = "Shaded"
        visible.append(obj)
        return obj

    def feature(key, label, shape, color, parent):
        obj = doc.addObject("Part::Feature", key)
        obj.Shape = shape
        return finish(obj, label, color, parent)

    def mirrored(key, label, source, color, parent):
        obj = doc.addObject("Part::Mirroring", key)
        obj.Source = source
        obj.Base, obj.Normal = V(0,0,0), X
        return finish(obj, label, color, parent)

    def prism_yz(points, x, width):
        pts = [V(x, y, z) for y, z in points]
        return Part.Face(Part.makePolygon(pts + pts[:1])).extrude(X * width)

    def cylinder(radius, height, origin, axis):
        return Part.makeCylinder(radius, height, V(*origin), axis)

    def box(x, y, z, dx, dy, dz):
        return Part.makeBox(dx, dy, dz, V(x, y, z))

    def block(key, label, origin, dims, color, parent):
        obj = doc.addObject("Part::Box", key)
        obj.Length, obj.Width, obj.Height = dims
        obj.Placement = A.Placement(V(*origin), A.Rotation())
        return finish(obj, label, color, parent)

    def obround(origin, along, across, normal, length, width, thickness):
        c = V(*origin)
        r = width / 2
        a, b = c - along * (length / 2 - r), c + along * (length / 2 - r)
        edges = [Part.makeLine(a + across*r, b + across*r),
                 Part.Arc(b + across*r, b + along*r, b - across*r).toShape(),
                 Part.makeLine(b - across*r, a - across*r),
                 Part.Arc(a - across*r, a - along*r, a + across*r).toShape()]
        return Part.Face(Part.Wire(edges)).extrude(normal * thickness)

    def display_rect(width, height, radius, y, depth):
        z = 0.0
        rect = box(-width/2+radius,y,z-height/2,width-2*radius,depth,height)
        rect = rect.fuse(box(-width/2,y,z-height/2+radius,width,depth,height-2*radius))
        corners = [cylinder(radius,depth,(x,y,zz),Y)
                   for x in (-width/2+radius,width/2-radius)
                   for zz in (z-height/2+radius,z+height/2-radius)]
        return rect.multiFuse(corners).removeSplitter()

    def side_capsule(x, y, z, length, width, depth):
        return obround((x, y, z), Z, Y, X, length, width, depth)

    def native_cut(key, label, base, tool, color, parent):
        cutter = doc.addObject("Part::Feature", key + "Tool")
        cutter.Shape = tool
        cutter.Label = label + " · 刀体"
        obj = doc.addObject("Part::Cut", key)
        obj.Base, obj.Tool = base, cutter
        base.Visibility = cutter.Visibility = False
        return finish(obj, label, color, parent)

    def raw(key, shape):
        obj = doc.addObject("Part::Feature", key)
        obj.Shape = shape
        return obj

    # An editable sketch drives the continuous front, roof and handle extrusion.
    profile = [(0,BASE_Z),(0,EAVE_Z),(HANDLE_FRONT,SHOULDER_Z),(HANDLE_FRONT,HANDLE_TOP),
               (HANDLE_REAR,HANDLE_TOP),(HANDLE_REAR,REAR_SHOULDER_Z),(CASE_DEPTH,REAR_EAVE_Z),
               (CASE_DEPTH-REAR_THICKNESS,INNER_EAVE_Z),(INNER_REAR,INNER_PEAK_Z),
               (INNER_FRONT,INNER_PEAK_Z),(FRONT_THICKNESS,FRONT_INNER_EAVE_Z),(FRONT_THICKNESS,BASE_Z)]
    section = doc.addObject("Sketcher::SketchObject", "FoldSection")
    section.Label = "壳体 YZ 截面 · 可编辑"
    section.Placement = A.Placement(V(-WIDTH/2,0,0), A.Rotation(V(1,1,1),120))
    for a,b in zip(profile, profile[1:] + profile[:1]):
        section.addGeometry(Part.LineSegment(V(*a,0),V(*b,0)),False)
    skin = doc.addObject("Part::Extrusion","FoldedSkin")
    skin.Base, skin.Dir, skin.Solid = section, X*WIDTH, True
    section.Visibility = False
    # Round top outer corners on the flange; preserve the crisp shoulder folds.
    doc.recompute()
    rounded = []
    for i, edge in enumerate(skin.Shape.Edges, 1):
        c = edge.CenterOfMass
        at_end = abs(abs(c.x)-WIDTH/2) < .01
        if at_end and abs(c.z-HANDLE_TOP) < .01:
            rounded.append((i, OUTER_CORNER_RADIUS, OUTER_CORNER_RADIUS))
        elif at_end and abs(c.y) < .01 and edge.Length > 140:
            rounded.append((i, 1.6, 1.6))
    fil = doc.addObject("Part::Fillet","CowlEdges")
    fil.Base, fil.Edges = skin, rounded
    skin.Visibility = False
    skin = fil
    normal = V(0,-SHOULDER_SLOPE,1)
    normal.normalize()
    def deck(x,y):
        return V(x,y,EAVE_Z+SHOULDER_SLOPE*y)
    # Local screen X is horizontal, +Z runs up the slope, +Y points into the case.
    display_pose=A.Placement(deck(0,DISPLAY_DECK_Y),A.Rotation(Y,normal*-1))
    def aperture_wire(width,height,radius,y):
        slab=display_rect(width,height,radius,y,.1)
        return next(f.OuterWire for f in slab.Faces
                    if f.BoundBox.YLength<1e-7 and abs(f.CenterOfMass.y-y)<1e-7)
    flare=Part.makeLoft([aperture_wire(*DISPLAY_OUTER_WINDOW,1.8,0),
                         aperture_wire(*DISPLAY_WINDOW,.6,.8)],True,True)
    screen_cut=display_rect(*DISPLAY_OUTER_WINDOW,1.8,-3,3).fuse(flare).fuse(
        display_rect(*DISPLAY_WINDOW,.6,.8,8.2)).removeSplitter()
    screen_cut.Placement=display_pose.multiply(screen_cut.Placement)
    holes = [obround((0,HANDLE_FRONT-2,SHOULDER_Z+HANDLE_HEIGHT/2), X,Z,Y,90,HANDLE_OPENING_HEIGHT,10),
             screen_cut,
             cylinder(FRONT_GRILLE_RADIUS,9,(0,-3,SPEAKER_CENTER_Z),Y),
             obround((0,SLOT_Y,145),X,Y,Z,124,SLOT_HEIGHT,HANDLE_TOP-145)]
    # Keep symmetric openings separate from the asymmetric control cutouts.
    common_tool = raw("SymmetricCowlTool",Part.makeCompound(holes))
    common_tool.Label = "居中开孔 · 提手／显示窗／格栅／碟口"
    symmetric_cowl = doc.addObject("Part::Cut","SymmetricCowl")
    symmetric_cowl.Label = "对称壳体 · 含提手及居中开孔"
    symmetric_cowl.Base, symmetric_cowl.Tool = skin, common_tool
    skin.Visibility = common_tool.Visibility = False
    controls = [Part.makeCylinder(r,12,deck(x,y)-normal*7,normal)
                for x,y,r in [(x,y,5.25) for _,_,x,y in BUTTONS]+[(52,20,3.6)]]
    volume=volume_shapes()
    volume_pose=A.Placement(deck(52,20),A.Rotation(Y,-normal))
    volume_pocket=volume['pocket'].copy()
    volume_pocket.Placement=volume_pose.multiply(volume_pocket.Placement)
    controls.append(volume_pocket)
    volume_recess=volume['recess'].copy()
    volume_recess.Placement=volume_pose.multiply(volume_recess.Placement)
    controls.append(volume_recess)
    native_cut("Cowl","整片折壳构造源 · 对称主体＋原操控开孔",symmetric_cowl,
               Part.makeCompound(controls),TEAL,shell)

    # P2 outlets are open through the full sidewall, without inset obstruction.
    panel_profile = [(FRONT_THICKNESS,BASE_Z),(CASE_DEPTH-REAR_THICKNESS,BASE_Z),(CASE_DEPTH-REAR_THICKNESS,INNER_EAVE_Z),
                     (INNER_REAR,INNER_PEAK_Z),(INNER_FRONT,INNER_PEAK_Z),(FRONT_THICKNESS,FRONT_INNER_EAVE_Z)]
    cy, cz = PORT_CENTER_Y, PORT_CENTER_Z
    x = -WIDTH/2
    base = raw("LPanelBlank",prism_yz(panel_profile,x,REAR_THICKNESS))
    left_panel = native_cut("LPanel","左侧壳 · 镜像源",base,
                            speaker_duct.left_panel_opening(),BLACK,shell)
    mirrored("RPanel","右侧壳 · 关联镜像",left_panel,BLACK,shell)

    # Build the left port and cavity, then mirror them exactly for the right.
    left=-WIDTH/2
    port=speaker_duct.left_port()
    # Compact symmetric cavities retain the complete driver envelopes.
    outer=box(-65,5,31.5,65,CHAMBER_DEPTH,89)
    inner=box(-62.5,4,34,61,CHAMBER_DEPTH-1.5,84)
    # The 63.4-degree front wall closes progressively in rear-down printing.
    # Its parallel inner face leaves 2.5 mm normal thickness without a long bridge.
    wing_points=[V(-CHAMBER_SIDE_X,5+2*(CHAMBER_SIDE_X-65),38),V(-65,5,38),
                 V(-64,5,38),V(-64,62.5,38),V(-CHAMBER_SIDE_X,62.5,38)]
    wing=Part.Face(Part.makePolygon(wing_points+[wing_points[0]])).extrude(Z*80)
    inner_front=5+2*(CHAMBER_SIDE_X-2.5-65)+2.5*math.sqrt(5)
    air_points=[V(-CHAMBER_SIDE_X+2.5,inner_front,40.5),
                V(-64,3+2.5*math.sqrt(5),40.5),V(-60,3+2.5*math.sqrt(5),40.5),
                V(-60,60,40.5),V(-CHAMBER_SIDE_X+2.5,60,40.5)]
    wing_air=Part.Face(Part.makePolygon(air_points+[air_points[0]])).extrude(Z*75)
    cavity=outer.fuse(wing).cut(inner.fuse(wing_air)).removeSplitter()
    # The shallow outer pocket accepts removable sealing putty after wiring.
    # Leave the proven driver seat and the rear-down print datum untouched.
    cavity=cavity.cut(Part.makeCompound(speaker_wires.exit_tools(-1))).removeSplitter()
    cavity=speaker_print.smooth_left_wing(cavity)
    cavity=speaker_duct.left_chamber(cavity)
    left_port = feature("LPort","左侧 · 圆角梯形开放出口及连续内斜面（并入 P2）",port,BLACK,shell)
    mirrored("RPort","右侧 · 圆角梯形开放出口及连续内斜面（并入 P2）",left_port,BLACK,shell)
    left_chamber = feature("LChamber","左声道 · 独立导管及圆角梯形短渐扩口（未调谐）",cavity,TEAL,supports)
    mirrored("RChamber","右声道 · 独立导管及圆角梯形短渐扩口（未调谐）",left_chamber,TEAL,supports)

    # Front grille, baffle and two rectangular driver envelopes.
    zc=SPEAKER_CENTER_Z
    radius=FRONT_GRILLE_RADIUS
    mesh_radius=radius+GRILLE_UNDERLAP
    bezel=cylinder(mesh_radius+.25,FRONT_THICKNESS-FRONT_GRILLE_RECESS,
                   (0,FRONT_GRILLE_RECESS,zc),Y).cut(cylinder(mesh_radius-.1,7,(0,-.1,zc),Y))
    feature("FrontBezel","面板下方 · 隐藏护网连接环",bezel,TEAL,shell)
    grille=cylinder(mesh_radius,FRONT_THICKNESS-FRONT_GRILLE_RECESS,(0,FRONT_GRILLE_RECESS,zc),Y)
    vents=[]
    grid_extent = int(mesh_radius / GRILLE_PITCH) + 1
    for row in range(-grid_extent,grid_extent+1):
        dz=row*GRILLE_PITCH
        for col in range(-grid_extent,grid_extent+1):
            dx=(col+.5*(row%2))*GRILLE_PITCH
            # The oversized sheet continues under the panel. The circular cowl
            # masks perimeter holes naturally; its visible aperture has no lip.
            if math.hypot(dx,dz)+GRILLE_HOLE_RADIUS<=mesh_radius-1:
                vents.append(cylinder(GRILLE_HOLE_RADIUS,FRONT_THICKNESS+1,(dx,FRONT_GRILLE_RECESS-.1,zc+dz),Y))
    feature("FrontGrille","中央双喇叭 · 内凹 2.5 mm 通孔护网",grille.cut(Part.makeCompound(vents)),TEAL,shell)
    width,height=SPEAKER_FLANGE
    cx=-SPEAKER_CENTER_X
    sx,sz=cx-width/2,zc-height/2
    seat=SPEAKER_SEAT_Y
    gap=SPEAKER_FIT_CLEARANCE

    def basket_prism(clearance, y, length):
        bw,bh=(size+2*clearance for size in SPEAKER_BASKET)
        blank=box(cx-bw/2,y,zc-bh/2,bw,length,bh)
        return blank.makeFillet(SPEAKER_CORNER_RADIUS+clearance,
                                [edge for edge in blank.Edges if edge.BoundBox.YLength>0])

    pitch_x,pitch_z=SPEAKER_HOLE_PITCH
    screw_axes=[(cx+dx,zc+dz) for dx in (-pitch_x/2,pitch_x/2) for dz in (-pitch_z/2,pitch_z/2)]
    flange=box(sx,seat-SPEAKER_FRONT_DEPTH,sz,width,SPEAKER_FRONT_DEPTH,height)
    flange=flange.cut([cylinder(SPEAKER_HOLE_DIAMETER/2,SPEAKER_FRONT_DEPTH+2,(x,seat-SPEAKER_FRONT_DEPTH-1,z),Y)
                       for x,z in screw_axes])
    driver=flange.fuse(basket_prism(0,seat,SPEAKER_REAR_DEPTH)).removeSplitter()
    left_driver=feature("LDriver","左声道 · 实测喇叭试装包络",driver,RUBBER,hardware)
    mirrored("RDriver","右声道 · 喇叭试装包络关联镜像",left_driver,RUBBER,hardware)

    # Front loading: a full flange entry leads to a 3 mm seat plate.
    # The four blind bosses remain part of P3; cut the basket opening last
    # so neither the bosses nor the seat can project into the trial profile.
    rim=box(sx-2,5,sz-2,width+4,47,height+4).cut(
        box(sx-gap,4.5,sz-gap,width+2*gap,48,height+2*gap))
    plate=box(sx-1,seat,sz-1,width+2,3,height+2)
    bosses=[cylinder(4,11.5,(x,seat,z),Y) for x,z in screw_axes]
    pilots=[cylinder(SPEAKER_PILOT_DIAMETER/2,SPEAKER_PILOT_DEPTH+.1,(x,seat-.1,z),Y)
            for x,z in screw_axes]
    frame=rim.fuse([plate]+bosses).cut([basket_prism(gap,seat-.1,43)]+pilots).removeSplitter()
    frame=speaker_print.make_left_frame_printable(frame)
    left_frame=feature("LDriverFrame","左喇叭试装座 · 四处盲底孔",frame,TEAL,supports)
    mirrored("RDriverFrame","右喇叭试装座 · 关联镜像",left_frame,TEAL,supports)
    apertures=[box(x-width/2-gap,4.5,sz-gap,width+2*gap,3,height+2*gap)
               for x in (-SPEAKER_CENTER_X,SPEAKER_CENTER_X)]
    baffle=box(-65,5,31.5,130,2,89).cut(Part.makeCompound(apertures))
    feature("FrontBaffle","双单元前障板",baffle,RUBBER,supports)

    # Narrow side gaps leave no room for full-height rear screw pillars.
    # Lower mounts flank the battery; upper mounts sit behind the drive.
    rear=prism_yz([(CASE_DEPTH-REAR_THICKNESS,BASE_Z),(CASE_DEPTH,BASE_Z),(CASE_DEPTH,REAR_EAVE_Z),
                   (CASE_DEPTH-REAR_THICKNESS,INNER_EAVE_Z)],-WIDTH/2,WIDTH)
    tray=box(-WIDTH/2+REAR_THICKNESS,FRONT_THICKNESS,BASE_Z,WIDTH-2*REAR_THICKNESS,CASE_DEPTH-FRONT_THICKNESS-REAR_THICKNESS,REAR_THICKNESS)
    feature("Back","后壳后壁 · 构造源",rear,BLACK,shell)
    feature("Base","后壳底板 · 构造源",tray,BLACK,shell)
    feet=[cylinder(4,3,(x,y,FEET_BOTTOM_Z),Z) for x in (-55,55) for y in (11,69)]
    feature("Feet","四个脚垫",Part.makeCompound(feet),RUBBER,ui)

    oled_pcb,oled_panel,oled_header,oled_left,oled_pilots,oled_frame,oled_pocket=oled_shapes()
    feature("Window","OLED 玻璃面板 · 34.5×23×1.4",oled_panel,GLASS,ui)
    # Raised luminous shapes are a display-content mockup, not printable parts.
    glyphs=[]
    def segment(x,z,w,h):
        glyphs.append(box(x,.85,z,w,.15,h))
    def digit(x,z,active):
        segments={'a':(x+.5,z+7,3,.55),'g':(x+.5,z+3.5,3,.55),
                  'd':(x+.5,z,3,.55),'f':(x,z+4,.55,2.8),
                  'b':(x+3.5,z+4,.55,2.8),'e':(x,z+.7,.55,2.6),
                  'c':(x+3.5,z+.7,.55,2.6)}
        for name in active: segment(*segments[name])
    digit(-13,-2,'abcdef')
    digit(-7,-2,'abc')
    # Play icon, battery outline and volume bars.
    pts=[V(1,.85,-1),V(1,.85,5),V(5,.85,2)]
    glyphs.append(Part.Face(Part.makePolygon(pts+[pts[0]])).extrude(Y*.15))
    bz=1
    battery=box(8,.85,bz,5,.15,3).cut(box(8.5,.8,bz+.5,4,.4,2))
    glyphs.extend([battery,box(13,.85,bz+1,.7,.15,1),box(9,.85,bz+.8,2.5,.15,1.4)])
    for i in range(8): segment(-13+i*3.4,-6,2.3,1.2)
    feature("StatusArt","显示内容示意 · 曲目 07 / 播放 / 电量 / 音量",Part.makeCompound(glyphs),PIXEL,ui)
    # Local +Y is depth below the exterior face. Separate caps bridge the
    # 5 mm panel; a measured 2.8 mm actuator alone cannot pass through it.
    button_mounts=[]
    button_pose=A.Placement(deck(-54,17.5),A.Rotation(Y,normal*-1))
    row_offset=8.5*math.sqrt(1+SHOULDER_SLOPE**2)
    retainer=button_retainer(row_offset)
    for key,label,x,y in BUTTONS:
        pose=A.Placement(deck(x,y),A.Rotation(Y,normal*-1))
        def placed(shape):
            shape.Placement=pose.multiply(shape.Placement)
            return shape
        body,marks=button_parts(key)
        shape=Part.makeCompound([body,marks])
        face_colors=[WHITE if any(face.isSame(mark) for mark in marks.Faces) else ORANGE
                     for face in shape.Faces]
        key_obj=feature(key+'Key',label+' · 双色键帽／白色功能标记',placed(shape),ORANGE,ui)
        # Shared interface faces occur only once in the compound's face list.
        key_obj.ViewObject.DiffuseColor=face_colors
        switch=box(-6,8.8,-6,12,3.2,12).fuse(cylinder(6,2.8,(0,6,0),Y)).removeSplitter()
        obj=feature(key+'Switch',label+' · 12×12×6；圆头 Ø12 保守包络',placed(switch),RUBBER,hardware)
        for prop,value in [('BodyThickness',3.2),('ActuatorHeight',2.8),('PinLengthAllowance',3.7)]:
            obj.addProperty('App::PropertyLength',prop,'Switch dimensions');setattr(obj,prop,value)
        obj.addProperty('App::PropertyString','Unverified','Switch dimensions')
        obj.Unverified='Actuator diameter, stroke, pin footprint and support contact require measurement; pins are not modeled.'
        socket=box(-7.8,4.7,-7.8,15.6,7.5,15.6)
        socket=socket.cut(cylinder(6.6,3.9,(0,4.6,0),Y))
        socket=socket.cut(cylinder(6.2,.4,(0,8.5,0),Y))
        socket=socket.cut(box(-6.2,8.8,-6.2,12.4,3.5,12.4))
        button_mounts.append(placed(socket.removeSplitter()))
    for x in (-14,14):
        boss=cylinder(2.3,11.8,(x,4.7,0),Y).cut(cylinder(.8,10,(x,7,0),Y))
        boss.Placement=button_pose.multiply(boss.Placement);button_mounts.append(boss)
    retainer.Placement=button_pose.multiply(retainer.Placement)
    # Preserve the existing DAC connector allowance, with 0.5 mm side clearance.
    retainer=retainer.cut(box(-71.5,32.5,157.5,9.6,18,11)).removeSplitter()
    feature('ButtonRetainer','四键焊线支架 · 两侧敞开／双点支承',retainer,TEAL,ui)
    feature('ButtonMounts','四键定位座与压板螺柱 · 并入 P1',Part.makeCompound(button_mounts),TEAL,supports)
    for key,name,label,color,parent in (
        ('knob','Knob','音量旋钮 · 黑白双色／下沉细十字／压配',KNOB_BLACK,ui),
        ('shaft','Encoder','B50K · Ø6.8 螺纹／Ø5.8 花轴／9.8 六角螺母',SILVER,hardware),
        ('body','VolumePot','B50K 插接模块 · PCB35×26.2×1.5／总厚15／绕轴90°',RUBBER,hardware)):
        shape=volume[key].copy();shape.Placement=volume_pose.multiply(shape.Placement)
        obj=feature(name,label,shape,color,parent)
        if name=='Knob':
            mark=shape.Solids[1]
            obj.ViewObject.DiffuseColor=[WHITE if any(face.isSame(f) for f in mark.Faces) else KNOB_BLACK
                                        for face in shape.Faces]
        if name=='VolumePot':
            obj.ViewObject.DiffuseColor=[color for solid,color in zip(shape.Solids,(RUBBER,PCB,WHITE,SILVER))
                                         for face in solid.Faces]
            for prop,value in [('PCBWidth',35),('PCBDepth',26.2),('PCBThickness',1.5),('ModuleThickness',15)]:
                obj.addProperty('App::PropertyLength',prop,'Volume control');setattr(obj,prop,value)
            obj.addProperty('App::PropertyAngle','ModuleRotation','Volume control');obj.ModuleRotation=90
        obj.addProperty('App::PropertyString','FitStatus','Volume control')
        obj.FitStatus='PCB module dimensions user-confirmed; body/shaft cross-section inherited from bare B50K. Connector and pin shapes are conservative blocks; exact footprints and printed fit unverified.'

    # Measured optical-drive envelope. Local front becomes +Z and underside +Y;
    # this mounting orientation reverses the user's left/right along machine X.
    dw,dt,dh = DRIVE
    bottom = DRIVE_TOP-dh
    front_y = DRIVE_DATUM_Y-dt
    # Maximum-thickness envelope is conservative: the exact front-lip length,
    # corner radii and underside transition are not yet measured.
    drive_outline=[(-64,bottom+35),(-64,DRIVE_TOP),(64,DRIVE_TOP),
                   (64,bottom),(-39,bottom)]
    points=[V(x,front_y,z) for x,z in drive_outline]
    drive_shape=Part.Face(Part.makePolygon(points+points[:1])).extrude(Y*dt)
    # Recess location follows the reported local right-hand 25.2 mm strip.
    drive_shape=drive_shape.cut(box(-64,DRIVE_DATUM_Y-4.5,bottom,25.2,4.5,dh))
    drive=feature("DriveBlank","UJ-898 · 实测外形／前端厚度保守包络",drive_shape,SILVER,hardware)
    hardware.removeObject(drive);visible.remove(drive)
    body=native_cut("Drive","UJ-898 · 底面朝后／竖装向上退碟",drive,
               box(-61.4,SLOT_Y-2.25,bottom+2,121.6,4.5,dh),SILVER,hardware)
    for name,value in [('MeasuredFrontThickness',10.8),('MeasuredRearThickness',9.5),
                       ('UndersideStepWidth',25.2),('UndersideStepHeight',4.5),
                       ('RearWallPadAllowance',1.0),('SlotDatumHeight',7.95)]:
        body.addProperty('App::PropertyLength',name,'Measured drive');setattr(body,name,value)
    body.addProperty('App::PropertyString','FitStatus','Measured drive')
    body.FitStatus='User measurements; conservative maximum thickness. Corner/step extent and SATA transverse envelope need physical confirmation.'
    # Adapter is removed before extracting the drive; it no longer sits on P3.
    adapter_y=DRIVE_DATUM_Y-(9.5+7)/2
    adapter_z=bottom-20.4
    adapter=box(28.3,adapter_y,adapter_z,37.7,7,20.4)
    adapter=adapter.fuse(cylinder(3.25,3,(66,DRIVE_DATUM_Y-4.75,adapter_z+10.2),X)).removeSplitter()
    plug=feature("Bridge","Slimline SATA · 37.7×7／后伸20.4／根部Ø6.5×3",adapter,RUBBER,hardware)
    plug.addProperty('App::PropertyString','FitStatus','Measured drive')
    plug.FitStatus='Measured housing and strain relief. Vertical centering is provisional; 38.8 x 9.5 x 20.4 envelope checked separately.'
    # One short central shelf avoids both the stepped edge and the connector.
    shelf=box(-20,front_y,bottom-2,40,CASE_DEPTH-REAR_THICKNESS-front_y,2)
    bosses=[box(x,front_y,115,3.7,CASE_DEPTH-REAR_THICKNESS-front_y,4).fuse(
        box(x,front_y+5,111,3.7,CASE_DEPTH-REAR_THICKNESS-front_y-5,8)) for x in (-68,64.3)]
    pilots=[cylinder(.8,9,(x,front_y-.1,117),Y) for x in (-66.15,66.15)]
    carrier=shelf.multiFuse(bosses).cut(Part.makeCompound(pilots)).removeSplitter()
    feature("DriveCarrier","光驱中央承托／双侧压条螺柱",carrier,BLACK,supports)
    retainer=box(-64,front_y-3,110,128,3,10).multiFuse([
        box(x,front_y-3,115,4,3,4) for x in (-68,64)]).cut(Part.makeCompound([
        cylinder(1.1,4,(x,front_y-3.5,117),Y) for x in (-66.15,66.15)])).removeSplitter()
    feature("DriveRetainer","光驱可拆压条 · 两枚名义M2×10／薄垫接触",retainer,TEAL,supports)
    # Roof slot is symmetric; the slightly off-centre measured opening fits within it.
    def inner_roof(y):
        return REAR_EAVE_Z+(CASE_DEPTH-y)*SHOULDER_SLOPE-ROOF_OFFSET_Z
    y0,y1=SLOT_Y-3.5,SLOT_Y+3.5
    guide=prism_yz([(y0,DRIVE_TOP+.5),(y1,DRIVE_TOP+.5),(y1,inner_roof(y1)),(y0,inner_roof(y0))],-63,126)
    guide=guide.cut(box(-62,SLOT_Y-SLOT_HEIGHT/2,DRIVE_TOP,124,SLOT_HEIGHT,30))
    feature("SlotGuide","后斜面进碟导向框 · 5.5 mm 喉口",guide,TEAL,supports)
    feature("DisplayPCB","SH1106 PCB · 35.4×33.5×1.2／四孔与底部缺口",oled_pcb,PCB,hardware)
    header=feature("DisplayHeader","OLED 弯针接头预留 · 图纸深度11.3／2.54节距",oled_header,RUBBER,hardware)
    header.addProperty('App::PropertyFloatList','PinCentersX').PinCentersX=[-3.81,-1.27,1.27,3.81]
    header.addProperty('App::PropertyStringList','PinLabels').PinLabels=['VCC','GND','SCL','SDA']
    feature('DisplayRetainer','OLED 可拆压框 · 四点承压／两侧锁紧',oled_frame,TEAL,ui)
    left=feature('DisplayMountLeft','OLED 左侧定位柱与压框螺柱',oled_left,TEAL,supports)
    left.Placement=display_pose.multiply(left.Placement)
    right=mirrored('DisplayMountRight','OLED 右侧支柱 · 原生镜像',left,TEAL,supports)
    doc.recompute()
    # This carrier already has world coordinates; it is not transformed below.
    feature('DisplayCarrier','OLED 四孔定位座 · 孔距30.4×28.5／外侧压框螺柱',
            Part.makeCompound([left.Shape,right.Shape]),TEAL,supports)

    # The integrated perfboard has its own seats above the unchanged amp shelf.
    lower=box(-51,5,120,102,54,2)
    feet=[box(x,yy,120.5,3,3,.5) for x in (-36,33) for yy in (5,57)]
    feature("AmpShelf","功放托板 · 支撑位置待测",
            lower.multiFuse(feet).removeSplitter(),TEAL,supports)
    block("Amp","TPA3118D2 · PCB 标称 66×53",(-33,6,123),(66,53,1.6),PCB,hardware)
    block("AmpChip","功放元件高度 15 mm 预留",(-33,6,124.6),(66,53,15),SILVER,hardware)
    posts=[cylinder(1.5,1,(xx,yy,122),Z) for xx in (-31,31) for yy in (8,57)]
    feature("AmpPads","功放支撑示意（非安装孔位）",Part.makeCompound(posts),TEAL,supports)
    board=feature("Perfboard","洞洞板 · 转 180°／右前缺口／左耳",perfboard.board_shape(),PCB,hardware)
    board.addProperty("App::PropertyStringList","MountingHoles","Perfboard")
    board.MountingHoles=[hole for _,_,_,hole in perfboard.MOUNTS]
    board.addProperty("App::PropertyLength","BoardThickness","Perfboard")
    board.BoardThickness=perfboard.BOARD_THICKNESS
    module_labels={
        "MCU":"ESP32-S3 N16R8 · PCB／USB 与 COM 插座留空",
        "MCUChip":"ESP32-S3 元件高度预留",
        "MCUSockets":"ESP32-S3 排母高度预留",
        "DAC":"PCM5102 · PCB",
        "DACChip":"PCM5102 元件高度预留",
        "DACSockets":"PCM5102 排母高度预留",
        "BuckA":"DCE001 A · 主控 5Vin",
        "BuckB":"DCE001 B · 光驱／桥接器 VBUS",
    }
    module_shapes=perfboard.module_shapes()
    for name,label in module_labels.items():
        feature(name,label,module_shapes[name],PCB if name in ("MCU","DAC","BuckA","BuckB") else RUBBER,hardware)
    for name,(plug,_,_) in perfboard.CONNECTORS.items():
        label={"Buttons":"四键 5 芯侧插","OLED":"OLED 4 芯直插","VolumeSwitch":"音量开关 2 芯直插"}[name]
        feature("XH"+name,"XH2.54 · "+label+"／插合包络",perfboard.box(*plug),WHITE,hardware)
    for i,(x,y,length,_) in enumerate(perfboard.MOUNTS,1):
        feature(f"PerfboardScrew{i}",f"洞洞板 M2×{length} 螺钉 {i} · 名义包络",
                perfboard.screw_shape(x,y,length),SILVER,hardware)
    bx,by,_=BATTERY
    block("Battery","5600 mAh 平排电池包 · 商品标称 112×70×20",(-bx/2,6,8),BATTERY,BLUE,hardware)
    # A centered open-ended tray leaves 1 mm at each side of the pack.
    # Lead routing and final retention require the physical pack; no invented holes.
    cradle=box(-bx/2-3,6,6,bx+6,by,2)
    cradle=cradle.multiFuse([box(x,6,8,2,50,12) for x in (-bx/2-3,bx/2+1)])
    feature("BatteryCradle","底部平排电池托盘 · 线材与固定方式待实测",cradle.removeSplitter(),TEAL,supports)

    # Move the complete display stack together, including the native PCB boxes.
    for name in ('Window','StatusArt','DisplayPCB','DisplayHeader','DisplayRetainer'):
        obj=doc.getObject(name)
        obj.Placement=display_pose.multiply(obj.Placement)

    doc.recompute()
    # Three connected PLA solids. Construction objects remain editable and hidden.
    construction=group("Construction", "00 · 隐藏构造源（非独立打印件）")
    def consolidate(key,label,names,extra,color,parent):
        members=[doc.getObject(n) for n in names]
        shape=members[0].Shape.copy().multiFuse([o.Shape for o in members[1:]]+extra).removeSplitter()
        for obj in members:
            for g in (shell,ui,supports,hardware):
                if obj in g.Group:g.removeObject(obj)
            construction.addObject(obj)
            if obj in visible:visible.remove(obj)
            obj.Visibility=False
        result=feature(key,label,shape,color,parent)
        result.addProperty("App::PropertyStringList","ConstructionObjects")
        result.ConstructionObjects=names
        return result

    # Four rear-access wells hold short screws against blind front-cover posts.
    # Upper wells clear the electronics from above; lower wells flank the battery.
    front_posts=[];rear_bosses=[];core_tabs=[];access_wells=[];post_clearances=[]
    for sign in (-1,1):
        for x,z,start,end,radius in [(sign*LOWER_FASTENER_X,LOWER_FASTENER_Z,4,11,2.8),(sign*29,179,24.5,36,3.5)]:
            post=cylinder(2.3,end-start,(x,start,z),Y).cut(cylinder(.8,5.6,(x,end-5.5,z),Y))
            front_posts.append(post)
            envelope=prism_yz(profile[:7]+[(CASE_DEPTH,BASE_Z)],-WIDTH/2,WIDTH)
            well=cylinder(radius,CASE_DEPTH-end-.4,(x,end+.4,z),Y).common(envelope)
            rear_bosses.append(well)
            access_wells.extend([cylinder(1.1,3,(x,end+.3,z),Y),
                                 cylinder(2.2,CASE_DEPTH-end-3.1,(x,end+3.2,z),Y)])
            post_clearances.append(cylinder(2.55,end-start+.5,(x,start-.1,z),Y))
        # Bridge the upper well to the rear slope from above, clear of the tool bore.
        rear_bosses.append(prism_yz([(44,181.3),(56,181.3),(56,188.3)],sign*29-2,4))
        for z in (27,124):
            x=sign*64
            boss=box(-INNER_HALF_WIDTH if sign<0 else 62,7,23 if z==27 else 120.5,INNER_HALF_WIDTH-62,7,8 if z==27 else 7.5)
            rear_bosses.append(boss.cut(cylinder(1.0,8,(x,6.5,z),Y)))
            # Brace the back of the seat with a 45-degree taper for rear-wall-down printing.
            # The extra millimetre overlaps the wall and seat; 8 mm of each leg is exposed.
            wall = INNER_HALF_WIDTH
            corners = [V(sign * px, y, z - 2) for px, y in
                       ((wall + 1, 13), (wall - 9, 13), (wall + 1, 23))]
            rib = Part.Face(Part.makePolygon(corners + corners[:1])).extrude(Z * 4)
            rear_bosses.append(rib)
            tab=box(-67 if sign<0 else 60,5,z-4,7,2,8)
            if z==27:tab=tab.fuse(box(-67 if sign<0 else 60,5,31,7,2,3))
            tab=tab.cut(cylinder(1.4,3,(x,4.5,z),Y)).cut(
                Part.makeCone(2.4,1.4,1,V(x,5,z),Y))
            core_tabs.append(tab)
    def source_part(name,shape):
        obj=raw(name,shape);construction.addObject(obj);obj.Visibility=False
        return name
    core_tab_names=[source_part('CarrierTab'+str(i),shape) for i,shape in enumerate(core_tabs)]
    front_post_name=source_part('FrontFastenerPosts',Part.makeCompound(front_posts))
    rear_fastener_cuts=source_part('RearFastenerCuts',Part.makeCompound(access_wells+post_clearances))
    perfboard_sources=[source_part(name,shape) for name,shape in
                       perfboard.carrier_sources(left_chamber.Shape.BoundBox.YMax).items()]
    oled_pilots.Placement=display_pose.multiply(oled_pilots.Placement)
    display_pilots=source_part('DisplayMountPilots',oled_pilots)
    oled_pocket.Placement=display_pose.multiply(oled_pocket.Placement)
    display_pocket=source_part('DisplayPocket',oled_pocket)
    for obj in (left,right):
        supports.removeObject(obj);construction.addObject(obj)
        visible.remove(obj);obj.Visibility=False
    # The 5 mm normal-offset seam ends exactly at the symmetric rear peak.
    # There is no vertical step or exposed rear-shell tip above the seam.
    seam_top_z=REAR_SHOULDER_Z
    seam_profile=[(FRONT_THICKNESS,0),(HANDLE_REAR,0),(HANDLE_REAR,seam_top_z),
                  (FRONT_THICKNESS,FRONT_INNER_EAVE_Z)]
    roof_region_shape=box(-WIDTH/2-1,HANDLE_REAR,0,WIDTH+2,
                          CASE_DEPTH-HANDLE_REAR+1,HANDLE_TOP+1)
    roof_region_shape=roof_region_shape.multiFuse([
        prism_yz(seam_profile,-WIDTH/2,REAR_THICKNESS),prism_yz(seam_profile,WIDTH/2-REAR_THICKNESS,REAR_THICKNESS)]).removeSplitter()
    roof_region=doc.getObject(source_part('RearRoofRegion',
        roof_region_shape))
    front_cowl=doc.addObject('Part::Cut','FrontCowl')
    front_cowl.Label='前壳折面与提手 · 后斜面已分离'
    front_cowl.Base,front_cowl.Tool=doc.Cowl,roof_region
    rear_roof=doc.addObject('Part::Common','RearRoof')
    rear_roof.Label='后斜面／碟口／侧缘直线交接 · 并入 P2'
    rear_roof.Base,rear_roof.Tool=doc.Cowl,roof_region
    shell.removeObject(doc.Cowl)
    construction.addObject(doc.Cowl)
    visible.remove(doc.Cowl)
    doc.Cowl.Visibility=False
    doc.recompute()
    front=consolidate("FrontShell","P1 · 一体前壳／提手／护网",
                      ['FrontCowl','FrontBezel','FrontGrille','ButtonMounts',front_post_name],[],ORANGE,shell)
    front.Shape=front.Shape.cut(doc.getObject(display_pocket).Shape).fuse(doc.DisplayCarrier.Shape).cut(
        doc.getObject(display_pilots).Shape).removeSplitter()
    front.ConstructionObjects=list(front.ConstructionObjects)+['DisplayCarrier']
    supports.removeObject(doc.DisplayCarrier);construction.addObject(doc.DisplayCarrier)
    visible.remove(doc.DisplayCarrier);doc.DisplayCarrier.Visibility=False
    core=consolidate("SpeakerCarrier","P3 · 双声腔／功放托板／洞洞板支架",
                     ['LChamber','RChamber','LDriverFrame','RDriverFrame','FrontBaffle','AmpShelf','AmpPads']
                     +core_tab_names+perfboard_sources,
                     [],TEAL,supports)
    rear=consolidate("RearShell","P2 · 一体后壳／左右圆角梯形开放出口",
                     ['RearRoof','SlotGuide','LPanel','RPanel','Back','Base','BatteryCradle','DriveCarrier','LPort','RPort'],rear_bosses,BLACK,shell)
    rear.Shape=rear.Shape.cut(doc.getObject(rear_fastener_cuts).Shape).removeSplitter()
    # Strap slots are outside the 112 mm pack. Straps are removed before sliding the pack out.
    strap_slots=[box(x,y,BASE_Z-.5,3,8,20) for x in (-61,58) for y in (24,44)]
    rear.Shape=rear.Shape.cut(Part.makeCompound(strap_slots)).removeSplitter()
    bottom_envelope = bottom_corner_envelope()
    for obj in (front, rear):
        obj.Shape = obj.Shape.common(bottom_envelope).removeSplitter()
        obj.addProperty('App::PropertyLength', 'BottomCornerRadius', 'Dimensions')
        obj.BottomCornerRadius = OUTER_CORNER_RADIUS
    for obj in (front,rear,core):
        if len(obj.Shape.Solids)!=1:
            raise RuntimeError(f"{obj.Name}: expected one connected solid, got {len(obj.Shape.Solids)}")


    cable_clearances=group("CableClearances","05 · 洞洞板线束和拔插预留")
    volumes={
        "PerfboardUnderWiring":perfboard.wiring_under_board(core.Shape),
        **{name:module_shapes[name] for name in ("BuckAService","BuckBService","DACPowerConnector")},
    }
    for name,(_,lead,service) in perfboard.CONNECTORS.items():
        volumes[name+"LeadBend"]=perfboard.box(*lead)
        volumes[name+"Unplug"]=perfboard.box(*service)
    for name in perfboard.HARNESS_ROUTES:
        volumes[name+"HarnessClosed"]=perfboard.harness_shape(name)
        volumes[name+"HarnessOpen"]=perfboard.harness_shape(name,perfboard.SERVICE_OPENING)
    volumes.update({name:perfboard.fixed_wire_shape(name) for name in perfboard.FIXED_WIRE_ROUTES})
    for name,shape in volumes.items():
        item=raw(name,shape)
        item.Label=name
        if name.endswith(("HarnessClosed","HarnessOpen")):
            item.Label=name.replace("HarnessClosed"," · 合壳线束").replace("HarnessOpen",f" · 前壳拉开 {perfboard.SERVICE_OPENING} mm")
        cable_clearances.addObject(item)
        item.ViewObject.ShapeColor=BLUE
        item.ViewObject.Transparency=65
        item.Visibility=False


    allowance=raw('SataPlugClearance',box(27.2,DRIVE_DATUM_Y-9.5,bottom-20.4,38.8,9.5,20.4))
    construction.addObject(allowance);allowance.Visibility=False
    wire=raw('SataCableClearance',box(64,DRIVE_DATUM_Y-26,bottom-13.45,CABLE_SIDE_ALLOWANCE,26,6.5))
    wire.Label='SATA 线缆走线预留 · 实测侧向14.5／侧壁余量1.5'
    construction.addObject(wire);wire.Visibility=False

    disc=raw("DiscReference",cylinder(60,1.2,(0,SLOT_Y-.6,180),Y).cut(
        cylinder(7.5,2,(0,SLOT_Y-1,180),Y)))
    disc.Label="参考 · 提手后竖直退碟（默认隐藏）"
    disc.ViewObject.ShapeColor=SILVER
    disc.ViewObject.DisplayMode="Shaded"
    disc.Visibility=False

    doc.recompute()
    for o in visible:
        o.Visibility = True
        if o.Shape.isNull() or not o.Shape.isValid() or not o.Shape.Solids:
            raise RuntimeError("Invalid solid: " + o.Name)
    # Let the newly created view initialize before assigning the saved camera.
    G.updateGui()
    loop = QtCore.QEventLoop()
    QtCore.QTimer.singleShot(1200, loop.quit)
    loop.exec_()
    G.activeDocument().activeView().setCameraOrientation(A.Rotation(Z,21).multiply(
        A.Rotation(X,76)).Q)
    G.activeDocument().activeView().fitAll()
    G.updateGui()
    loop = QtCore.QEventLoop()
    QtCore.QTimer.singleShot(1200, loop.quit)
    loop.exec_()
    doc.recompute()
    doc.saveAs(str(folder/"Discora.FCStd"))
    return doc, visible


target = os.environ.get("DISCORA_CAD_OUTPUT") or QtWidgets.QFileDialog.getExistingDirectory(
    None, "选择 Discora 模型输出目录")
if target:
    build(Path(target))
