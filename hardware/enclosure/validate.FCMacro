"""Reopen the saved three-part PLA model and validate static B-rep geometry."""
import hashlib
import json
import math
import os
from pathlib import Path
import FreeCAD as A
import Part
from PySide import QtWidgets


def validate(folder):
    model=folder/'Discora.FCStd';doc=A.openDocument(str(model))
    objects=[o for g in ('Shell','Controls','Carrier','Hardware') for o in doc.getObject(g).Group]
    tolerance=.001
    invalid=[o.Name for o in objects if o.Shape.isNull() or not o.Shape.isValid() or not o.Shape.Solids]
    assert not invalid,invalid
    def collisions(shape,candidates):
        hits=[];a=shape.BoundBox
        for o in candidates:
            b=o.Shape.BoundBox
            if any(min(getattr(a,k+'Max'),getattr(b,k+'Max'))-max(getattr(a,k+'Min'),getattr(b,k+'Min'))<1e-7 for k in 'XYZ'):continue
            volume=shape.common(o.Shape).Volume
            if volume>tolerance:hits.append({'object':o.Name,'volume_mm3':volume})
        return hits
    clashes=[]
    intentional_press_fit=[]
    for i,o in enumerate(objects):
        for hit in collisions(o.Shape,objects[i+1:]):
            if {o.Name,hit['object']}=={'Knob','Encoder'}:
                # Only the six crush-rib tips may enter the spline envelope.
                # Do not exempt this pair wholesale: cap the interference and
                # reject any overlap outside the specified 0.1 mm radial band.
                pose=A.Placement(A.Vector(52,20,165+20*27/38),
                                 A.Rotation(A.Vector(0,1,0),A.Vector(0,27/38,-1)))
                band=Part.makeCylinder(2.9001,7.0002,A.Vector(0,-10.2001,0),A.Vector(0,1,0)).cut(
                    Part.makeCylinder(2.7999,7.0002,A.Vector(0,-10.2001,0),A.Vector(0,1,0)))
                band.Placement=pose
                overlap=doc.Knob.Shape.common(doc.Encoder.Shape)
                residual=overlap.cut(band).Volume
                assert 0<hit['volume_mm3']<4.2 and residual<=tolerance,(hit,residual)
                intentional_press_fit.append({'first':o.Name,**hit,'outside_allowed_band_mm3':residual,
                    'physical_retention_verified':False})
            else:clashes.append({'first':o.Name,**hit})
    print('STATIC_CLASHES',clashes,flush=True)
    main=['FrontShell','RearShell','SpeakerCarrier']
    connected={n:len(doc.getObject(n).Shape.Solids) for n in main}
    assert all(n==1 for n in connected.values()),connected
    roof_ownership={}
    for name in ('RearRoof','SlotGuide'):
        source=doc.getObject(name).Shape.cut(doc.RearFastenerCuts.Shape)
        roof_ownership[name]={'intersection_with_front_mm3':source.common(doc.FrontShell.Shape).Volume,
                              'missing_from_rear_mm3':source.cut(doc.RearShell.Shape).Volume}
        assert name in doc.RearShell.ConstructionObjects and name not in doc.FrontShell.ConstructionObjects
        assert all(abs(v)<=tolerance for v in roof_ownership[name].values()),roof_ownership
    assert abs(doc.FrontShell.Shape.BoundBox.YMax-49.0)<1e-7
    # Extend the saved inner slope to the handle rear plane. Its endpoint must
    # meet the rear roof peak directly, without a vertical step.
    seam_start=doc.FoldSection.Geometry[10].StartPoint
    inner_slope=doc.FoldSection.Geometry[9]
    seam_slope=(inner_slope.StartPoint.y-inner_slope.EndPoint.y)/(inner_slope.StartPoint.x-inner_slope.EndPoint.x)
    rear_y=doc.FoldSection.Geometry[5].StartPoint.x
    seam_end=A.Vector(rear_y,seam_start.y+(rear_y-seam_start.x)*seam_slope,0)
    assert abs(seam_end.y-doc.FoldSection.Geometry[5].StartPoint.y)<1e-7
    seam_points=[]
    for x in (-84,84):
        for y in (6,12,24,35,38,40,42.4):
            z=seam_start.y+(y-seam_start.x)*(seam_end.y-seam_start.y)/(seam_end.x-seam_start.x)
            assert doc.FrontShell.Shape.isInside(A.Vector(x,y,z+.05),1e-6,True)
            assert doc.RearShell.Shape.isInside(A.Vector(x,y,z-.05),1e-6,True)
            seam_points.append([x,y,z])
    # Measure thickness on the saved solid, along each panel's normal.
    slope=27/38;normal=A.Vector(0,-slope,1);normal.normalize()
    thickness={}
    def section_length(name,point,axis):
        probe=Part.makeLine(point-axis*10,point+axis*10)
        return sum(edge.Length for edge in doc.getObject(name).Shape.common(probe).Edges)
    for x,z in [(-60,150),(60,150),(-67,80),(67,80),(0,6)]:
        thickness[f'vertical_{x}_{z}']=section_length('FrontShell',A.Vector(x,0,z),A.Vector(0,1,0))
    # Keep panel probes outside the two added blind mounting posts at X=±29.
    for x,y in [(-30,8),(30,8),(-25,30),(25,30),(50,32)]:
        thickness[f'slope_{x}_{y}']=section_length('FrontShell',A.Vector(x,y,165+slope*y),normal)
    for x in (-84,84):
        for y in (5,12,24,32,37):
            thickness[f'slope_side_{x}_{y}']=section_length('FrontShell',A.Vector(x,y,165+slope*y),normal)
    thickness['grille']=section_length('FrontGrille',A.Vector(1.45,0,76),A.Vector(0,1,0))
    thickness['handle']=section_length('FrontShell',A.Vector(60,46.5,211),A.Vector(0,1,0))
    # The PCB-module pocket extends beneath this shoulder sample; its local
    # floor is 3.6 mm, while the recessed nut clamps 2 mm (check-volume.py).
    expected_thickness={'grille':2.5,'slope_50_32':3.6}
    assert all(abs(value-expected_thickness.get(name,5))<1e-6 for name,value in thickness.items()),thickness
    print('PANEL_THICKNESS',thickness,flush=True)
    # Check the finished front shell, not just its hidden circular cutter.
    mouth=Part.makeCylinder(65,2.5-2e-5,A.Vector(0,1e-5,76),A.Vector(0,1,0))
    mouth_obstruction=doc.FrontShell.Shape.common(mouth).Volume
    circles=[e.Curve.Radius for e in doc.FrontShell.Shape.Edges
             if isinstance(e.Curve,Part.Circle)
             and (e.Curve.Center-A.Vector(0,0,76)).Length<1e-6
             and abs(e.Length-2*math.pi*65)<1e-5]
    recess=doc.FrontGrille.Shape.BoundBox.YMin
    grille_check={'opening_diameter_mm':130,'recess_mm':recess,
                  'grille_thickness_mm':doc.FrontGrille.Shape.BoundBox.YLength,
                  'mouth_obstruction_mm3':mouth_obstruction,
                  'complete_front_circle_radii_mm':circles,
                  'grille_back_y_mm':doc.FrontGrille.Shape.BoundBox.YMax,
                  'driver_front_gap_mm':doc.LDriver.Shape.BoundBox.YMin-doc.FrontGrille.Shape.BoundBox.YMax}
    assert circles and all(abs(r-65)<1e-6 for r in circles),grille_check
    assert mouth_obstruction<=tolerance and abs(recess-2.5)<1e-6,grille_check
    assert abs(grille_check['grille_back_y_mm']-5)<1e-6 and abs(grille_check['driver_front_gap_mm']-3)<1e-6,grille_check
    # Check the final P3, where fusion could otherwise fill a pilot or aperture.
    axis=A.Vector(0,1,0)
    carrier=doc.SpeakerCarrier.Shape
    speaker_mount={'seat_y_mm':10,'trial_opening_zx_mm':[71.5,39.3],
                   'opening_corner_radius_mm':12.5,'hole_pitch_zx_mm':[70,36],
                   'driver_hole_diameter_mm':3.3,'pilot_diameter_mm':2.3,'pilot_depth_mm':10.5,
                   'screw_thread_diameter_mm':2.8,'screw_thread_length_mm':9.5,'screw_head_height_mm':1.9,
                   'reserved_screw_head_diameter_mm':6,'screw_head_diameter_measured':False,
                   'mounts':{}}
    for name,cx in [('LDriver',-26),('RDriver',26)]:
        driver=doc.getObject(name).Shape
        bb=driver.BoundBox
        assert abs(bb.YMin-8)<1e-7 and abs(bb.YMax-49)<1e-7
        footprint=Part.makeBox(46,0.2,81,A.Vector(cx-23,10.8,35.5))
        clear_sections=footprint.cut(carrier).Solids
        aperture=next(solid for solid in clear_sections if solid.isInside(A.Vector(cx,10.9,76),1e-7,False))
        opening=aperture.BoundBox
        assert abs(opening.XLength-39.3)<1e-7 and abs(opening.ZLength-71.5)<1e-7
        assert any(isinstance(face.Surface,Part.Cylinder) and abs(face.Surface.Radius-12.5)<1e-7
                   for face in aperture.Faces)
        entry=Part.makeBox(bb.XLength,10,bb.ZLength,A.Vector(bb.XMin,0,bb.ZMin))
        basket=driver.common(Part.makeBox(46,40,81,A.Vector(cx-23,10,35.5)))
        # Extruded basket proxy: sweep the maximum modeled section from the front
        # along the insertion axis to its fully seated position.
        section=[face for face in basket.Faces if abs(face.BoundBox.YMin-10)<1e-7 and face.BoundBox.YLength<1e-7]
        assert len(section)==1
        entry_clash=entry.common(carrier).Volume
        basket_sweep=section[0].translated(A.Vector(0,-10,0)).extrude(axis*49)
        basket_clash=basket_sweep.common(carrier).Volume
        assert max(entry_clash,basket_clash)<=tolerance
        holes=[]
        for x in (cx-18,cx+18):
            for z in (41,111):
                def bore(radius,y,height):
                    return Part.makeCylinder(radius,height,A.Vector(x,y,z),axis)
                pilot=bore(1.15,10,10.5)
                wall=bore(3,10,10.5).cut(pilot)
                bottom=bore(1.15,20.5,1)
                shank=bore(1.4,8,2)
                head=bore(3,6.1,1.9)
                tool=bore(3,0,8)
                seat=bore(3,10,.1).cut(bore(1.65,10,.1))
                hole=dict(center_xz_mm=[x,z],pilot_obstruction_mm3=pilot.common(carrier).Volume,
                          missing_pilot_wall_mm3=wall.cut(carrier).Volume,
                          missing_pilot_bottom_mm3=bottom.cut(carrier).Volume,
                          seat_obstruction_mm3=seat.cut(carrier).Volume,
                          screw_shank_obstruction_mm3=shank.common(driver).Volume,
                          reserved_head_clashes=collisions(head,objects),
                          front_tool_clashes=collisions(tool,[obj for obj in objects if obj.Name!='FrontShell']))
                assert all(value<=tolerance for key,value in hole.items() if key.endswith('_mm3')),hole
                assert not hole['reserved_head_clashes'] and not hole['front_tool_clashes'],hole
                holes.append(hole)
        speaker_mount['mounts'][name]={'entry_clash_mm3':entry_clash,'basket_sweep_clash_mm3':basket_clash,'holes':holes}
    speaker_mount['rear_gap_mm']=doc.LChamber.Shape.BoundBox.YMax-2.5-doc.LDriver.Shape.BoundBox.YMax
    assert abs(speaker_mount['rear_gap_mm']-11)<1e-7
    # The larger sheet is masked by the smaller panel opening. Read the final
    # hole walls to distinguish complete circles from exposed circular segments.
    hole_walls=[f for f in doc.FrontShell.Shape.Faces
                if isinstance(f.Surface,Part.Cylinder) and abs(f.Surface.Radius-.94)<1e-6]
    areas={}
    for face in hole_walls:
        key=(round(face.Surface.Center.x,6),round(face.Surface.Center.z-76,6))
        areas[key]=areas.get(key,0)+face.Area
        assert abs(face.BoundBox.YMin-2.5)<1e-6 and abs(face.BoundBox.YMax-5)<1e-6
    centers=set(areas)
    source_centers={(round((col+.5*(row%2))*2.9,6),round(row*2.9,6))
                    for row in range(-24,25) for col in range(-24,25)
                    if math.hypot((col+.5*(row%2))*2.9,row*2.9)+.94<=67}
    expected={p for p in source_centers if math.hypot(*p)-.94<65}
    full={p for p in expected if math.hypot(*p)+.94<=65}
    partial=expected-full
    assert centers==expected and len(full)==1531 and len(partial)==92,(len(centers),len(full),len(partial))
    full_wall_area=2*math.pi*.94*2.5
    assert all(abs(areas[p]-full_wall_area)<1e-5 for p in full)
    assert all(0<areas[p]<full_wall_area-1e-5 for p in partial)
    assert all((-x,z) in centers for x,z in centers)
    source_walls=[f for f in doc.FrontGrille.Shape.Faces
                  if isinstance(f.Surface,Part.Cylinder) and abs(f.Surface.Radius-.94)<1e-6]
    assert len(source_walls)==1627 and abs(doc.FrontGrille.Shape.BoundBox.XLength-136)<1e-6
    grille_check.update(sheet_diameter_mm=136,panel_underlap_mm=3,source_hole_count=len(source_walls),
                        exposed_hole_count=len(centers),complete_exposed_holes=len(full),
                        partially_masked_edge_holes=len(partial),fully_masked_holes=len(source_centers-expected),
                        continuous_visible_rim=False,minimum_hole_web_mm=2.9-1.88)
    print('RECESSED_GRILLE',grille_check,flush=True)
    mirror=A.Matrix();mirror.A11=-1
    def reflected(shape):
        s=shape.copy();s.transformShape(mirror,True);return s
    def difference(a,b):return a.cut(b).Volume+b.cut(a).Volume
    symmetry={}
    for left,right in [('LPort','RPort'),('LDriver','RDriver'),('LChamber','RChamber'),('LDriverFrame','RDriverFrame'),('Window','Window')]:
        symmetry[left+' / '+right]=difference(reflected(doc.getObject(left).Shape),doc.getObject(right).Shape)
    rear=doc.RearShell.Shape
    symmetry['RearShell']=difference(rear,reflected(rear))
    # The lower speaker structure, including baffle and mounting tabs, is symmetric.
    low=doc.SpeakerCarrier.Shape.common(Part.makeBox(300,200,220.5,A.Vector(-150,-50,-100)))
    symmetry['SpeakerCarrier below Z=120.5']=difference(low,reflected(low))
    exceptions=doc.CowlTool.Shape.multiFuse([reflected(doc.CowlTool.Shape),doc.ButtonMounts.Shape,reflected(doc.ButtonMounts.Shape)])
    front=doc.FrontShell.Shape
    # The dense grille already passed the independent symmetric hole-pattern
    # and circular mouth checks above. Compare the shell outside that zone.
    grille_zone=Part.makeCylinder(68.1,9,A.Vector(0,-1,76),A.Vector(0,1,0))
    symmetry['FrontShell (control details and checked grille excepted)']=difference(
        front.cut(grille_zone).cut(exceptions),reflected(front.cut(grille_zone)).cut(exceptions))
    print('SYMMETRY',symmetry,flush=True)
    links={n:(doc.getObject(n).TypeId=='Part::Mirroring' and doc.getObject(n).Source.Name==n.replace('R','L',1)) for n in ('RPort','RDriver','RChamber','RDriverFrame')}
    slot_y=doc.Drive.Tool.Shape.BoundBox.Center.y
    sweep=Part.makeBox(120,1.2,300,A.Vector(-60,slot_y-.6,doc.Drive.Shape.BoundBox.ZMin+2))
    disc=collisions(sweep,objects)
    # Read alignment from saved geometry, independently of build parameters.
    handle_y=(doc.FoldSection.Geometry[2].StartPoint.x+doc.FoldSection.Geometry[4].StartPoint.x)/2
    shoulders={}
    for name,index in [('front',1),('rear',5)]:
        edge=doc.FoldSection.Geometry[index]
        run=abs(edge.EndPoint.x-edge.StartPoint.x)
        rise=abs(edge.EndPoint.y-edge.StartPoint.y)
        shoulders[name]={'horizontal_width_mm':run,'rise_mm':rise,
                         'surface_width_mm':math.hypot(run,rise),
                         'angle_deg':math.degrees(math.atan2(rise,run))}
    assert all(abs(shoulders['front'][k]-shoulders['rear'][k])<1e-7 for k in shoulders['front']),shoulders
    shoulder_z=doc.FoldSection.Geometry[2].StartPoint.y
    handle_top=doc.FoldSection.Geometry[3].StartPoint.y
    port_alignment={'handle_center_y_mm':handle_y,
        'rear_outline_center_y_mm':(rear.BoundBox.YMin+rear.BoundBox.YMax)/2,
        'port_center_y_mm':{n:doc.getObject(n).Shape.BoundBox.Center.y for n in ('LPort','RPort')},
        'shell_opening_center_y_mm':doc.LPanelTool.Shape.BoundBox.Center.y}
    paths={}
    for side,sign in [('L',-1),('R',1)]:
        # Enter the independent duct above Z=98, descend, then exit at Z=65.
        points=[(sign*26,55,76),(sign*52,55,76),(sign*52,55,103),
                (sign*65.5,55,103),(sign*65.5,55,65),(sign*87,55,65)]
        parts=[]
        for a,b in zip(points,points[1:]):
            a,b=A.Vector(*a),A.Vector(*b);parts.append(Part.makeCylinder(.4,(b-a).Length,a,b-a))
        paths[side]={'points_mm':points,'probe_radius_mm':.4,'clashes':collisions(Part.makeCompound(parts),objects)}
    reservations=[
        ('amp_input',(-48,6,123),(15,53,16.6),('Amp','AmpChip','SpeakerCarrier')),
        ('amp_output',(33,6,123),(15,53,16.6),('Amp','AmpChip','SpeakerCarrier'))]
    keepouts={}
    # Check support structures too, excluding only the original pad solids from
    # their owners. A whole integrated carrier must not hide connector conflicts.
    support_free={'SpeakerCarrier':doc.SpeakerCarrier.Shape.cut(doc.AmpPads.Shape)}
    for name,origin,size,owners in reservations:
        shape=Part.makeBox(*size,A.Vector(*origin))
        hits=collisions(shape,[o for o in objects if o.Name not in owners])
        for owner in owners:
            if owner in support_free:
                volume=shape.common(support_free[owner]).Volume
                if volume>tolerance:hits.append({'object':owner,'volume_mm3':volume})
        keepouts[name]={'origin_mm':origin,'size_mm':size,'clashes':hits}
    harness=Part.makeCylinder(1,12,A.Vector(50,30,136),A.Vector(0,0,1))
    keepouts['volume_harness']={'radius_mm':1,'origin_mm':[50,30,136],'height_mm':12,'clashes':collisions(harness,objects)}
    clearances={}
    for a,b in [('Battery','FrontShell'),('Battery','SpeakerCarrier'),('MCUChip','FrontShell'),('Drive','Perfboard'),('VolumePot','Perfboard')]:
        clearances[a+' / '+b]=doc.getObject(a).Shape.distToShape(doc.getObject(b).Shape)[0]
    battery=doc.Battery.Shape.BoundBox
    battery_fit={'supplier_size_xyz_mm':[112,70,20],'model_size_xyz_mm':[battery.XLength,battery.YLength,battery.ZLength],
                 'origin_xyz_mm':[battery.XMin,battery.YMin,battery.ZMin],
                 'front_inner_wall_gap_mm':battery.YMin-5,'rear_inner_wall_gap_mm':doc.Back.Shape.BoundBox.YMin-battery.YMax,
                 'cradle_side_gap_mm':1,'lead_and_connector_envelope_verified':False,'retention_verified':False}
    controls={};baseline_path=os.environ.get('DISCORA_CAD_BASELINE')
    if baseline_path:
        baseline=A.openDocument(baseline_path)
        for n in ('Window','StatusArt','Knob','DisplayPCB','DisplayHeader','DisplayCarrier'):
            previous=baseline.getObject(n).Shape.copy()
            previous.translate(A.Vector(0,0,15))
            controls[n]=difference(previous,doc.getObject(n).Shape)
        controls['source_model_sha256']=hashlib.sha256(Path(baseline_path).read_bytes()).hexdigest()
        A.closeDocument(baseline.Name)
    bb=Part.makeCompound([o.Shape for o in objects]).BoundBox
    handle=collisions(Part.makeBox(50,10,22,A.Vector(-25,handle_y-5,shoulder_z+11.5)),objects)
    report={'date':'2026-11-14','model':model.name,'sha256':hashlib.sha256(model.read_bytes()).hexdigest(),
        'version':A.Version()[:3],'items':len(objects),'objects':[o.Name for o in objects],
        'main_pla_parts':connected,'rigid_pla_pieces':['FrontShell','RearShell','SpeakerCarrier','PlayPauseKey','EjectKey','PrevKey','NextKey','ButtonRetainer','DisplayRetainer','DriveRetainer','Knob'],
        'rear_roof_ownership':roof_ownership,'shell_split_y_mm':49.0,
        'straight_side_seam_yz_mm':[[seam_start.x,seam_start.y],[seam_end.x,seam_end.y]],
        'side_seam_ownership_samples_xyz_mm':seam_points,
        'invalid':invalid,'intersection_tolerance_mm3':tolerance,'clashes':clashes,
        'intentional_press_fit':intentional_press_fit,
        'assembly_size_xyz_mm':[bb.XLength,bb.YLength,bb.ZLength],
        'mirror_plane':'X=0','mirror_difference_mm3':symmetry,'native_mirror_links':links,
        'disc':disc,'disc_sweep_mm':{'origin':[-60,slot_y-.6,doc.Drive.Shape.BoundBox.ZMin+2],'size':[120,1.2,300]},
        'side_port_handle_alignment':port_alignment,'side_air_paths':paths,'connector_allowances':keepouts,'key_clearances_mm':clearances,
        'battery_fit':battery_fit,'controls_translation_xyz_mm':[0,0,15],
        'top_shoulders':shoulders,'front_panel_thickness_samples_mm':thickness,
        'recessed_grille':grille_check,'speaker_mount':speaker_mount,
        'original_controls_difference_mm3':controls,'handle_opening_mm':[90,24],'handle_passage_clashes':handle,
        'physical_validation':False,'acoustic_tuning_verified':False,
        'limits':['Speaker trial uses measured depth, hole pitch and basket extrema; exact profile, screw head diameter/thread type, terminals, gaskets and excursion remain unverified.',
                  'PCB sizes are documented; component heights and connector reservations are provisional.',
                  'Three main PLA solids and nominal screw/pilot bores do not validate printed strength or screw fit.',
                  'Separate assembly-path report distinguishes continuous conservative sweeps from sampled cover motion.',
                  'Battery leads, straps, connectors, bridge cables and power modules are not validated.',
                  'Side passages remain untuned; geometric continuity is not acoustic validation.']}
    (folder/'validation.json').write_text(json.dumps(report,ensure_ascii=False,indent=2)+'\n')
    assert abs(handle_y-46.5)<1e-7
    # Port placement now follows the P3 duct, not the side-panel midpoint.
    assert abs(port_alignment['port_center_y_mm']['LPort']-port_alignment['port_center_y_mm']['RPort'])<1e-7
    assert abs(doc.LPort.Shape.BoundBox.Center.z-65)<1e-7
    assert abs(doc.LPanelTool.Shape.BoundBox.Center.z-65)<1e-7
    assert not clashes and not disc and not handle,(clashes,disc,handle)
    assert all(v<=tolerance for v in symmetry.values()),symmetry
    assert all(links.values()),links
    assert all(not p['clashes'] for p in paths.values()),paths
    assert all(not p['clashes'] for p in keepouts.values()),keepouts
    assert all(v>=1-1e-7 for v in clearances.values()),clearances
    assert abs(handle_top-(165+44*27/38+45))<1e-7
    assert all(abs(a-b)<1e-7 for a,b in zip(report['assembly_size_xyz_mm'],[170,93,handle_top+2]))
    assert all(abs(a-b)<1e-7 for a,b in zip(battery_fit['model_size_xyz_mm'],[112,70,20]))
    assert all(v<=tolerance for k,v in controls.items() if k!='source_model_sha256'),controls
    print('PASS: three connected PLA solids, interference, symmetry, disc and air paths',flush=True)
    return doc


target=os.environ.get('DISCORA_CAD_OUTPUT') or QtWidgets.QFileDialog.getExistingDirectory(None,'选择 Discora 模型目录进行验证')
if target:validate(Path(target))
