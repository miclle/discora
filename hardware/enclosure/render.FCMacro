"""Render review images from the saved FreeCAD model; do not save visibility changes."""
import os
from pathlib import Path
import FreeCAD as A
import FreeCADGui as G
import Part
from pivy import coin  # Register Coin camera wrappers used for export framing.
from PySide import QtWidgets, QtCore


def render(folder):
    doc=A.openDocument(str(folder/'Discora.FCStd'))
    visibility = {o.Name:o.Visibility for o in doc.Objects}
    G.updateGui()
    loop=QtCore.QEventLoop(); QtCore.QTimer.singleShot(1200,loop.quit); loop.exec_()
    view=G.activeDocument().activeView()
    camera = view.getCameraOrientation().Q
    view.setCameraType('Orthographic')
    def save(name,rotation,focus=None,height=None,size=(1000,1100)):
        # Set the Coin camera directly to avoid animated intermediate views.
        view.getCameraNode().orientation.setValue(coin.SbRotation(*rotation.Q))
        G.updateGui(); QtWidgets.QApplication.processEvents()
        loop=QtCore.QEventLoop(); QtCore.QTimer.singleShot(1200,loop.quit); loop.exec_()
        view.fitAll()
        # Keep margin when the export aspect differs from the GUI viewport.
        camera_node=view.getCameraNode()
        camera_node.height.setValue(camera_node.height.getValue()*1.25)
        if focus is not None:
            position=focus+rotation.multVec(A.Vector(0,0,500))
            camera_node.position.setValue(position.x,position.y,position.z)
            camera_node.height.setValue(height)
            camera_node.nearDistance.setValue(.1)
            camera_node.farDistance.setValue(2000)
        G.updateGui(); QtWidgets.QApplication.processEvents()
        view.saveImage(str(folder/name),*size,'White')
    front=A.Rotation(A.Vector(1,0,0),90)
    angle=A.Rotation(A.Vector(0,0,1),21).multiply(A.Rotation(A.Vector(1,0,0),76))
    save('preview.png',angle)
    save('front.png',front)
    save('grille-detail.png',angle,A.Vector(0,1,76),150)
    save('controls.png',A.Rotation(A.Vector(1,0,0),48))
    save('oled-front-detail.png',front,A.Vector(0,18,190),65,(1400,600))
    save('side.png',A.Rotation(A.Vector(0,0,1),90).multiply(front))
    save('topload.png',A.Rotation(A.Vector(0,0,1),155).multiply(A.Rotation(A.Vector(1,0,0),55)))
    doc.DiscReference.Visibility=True
    save('disc-path.png',angle)
    doc.DiscReference.Visibility=False
    for name in ['FrontShell','Window','StatusArt','PlayPauseKey','EjectKey','PrevKey','NextKey','ButtonRetainer','PlayPauseSwitch','EjectSwitch','PrevSwitch','NextSwitch','Knob','Encoder','VolumePot','DisplayPCB','DisplayHeader','DisplayRetainer']:
        doc.getObject(name).Visibility=False
    save('layout.png',angle)
    # Section through the left driver center, viewed from +X, reveals the depth stack.
    section=A.newDocument("DiscoraDepthSection")
    clip=Part.makeBox(74,200,300,A.Vector(-100,-20,-10))
    for group in ('Shell','Controls','Carrier','Hardware'):
        for source in doc.getObject(group).Group:
            if not hasattr(source,'Shape'): continue
            shape=source.Shape.common(clip)
            if shape.isNull() or not shape.Solids: continue
            obj=section.addObject('Part::Feature',source.Name)
            obj.Shape=shape
            obj.Label=source.Label
            obj.ViewObject.ShapeColor=source.ViewObject.ShapeColor
            obj.ViewObject.DisplayMode='Flat Lines'
            obj.ViewObject.LineColor=(.12,.15,.17)
    section.recompute()
    section_view=G.activeDocument().activeView()
    right=A.Rotation(A.Vector(0,0,1),90).multiply(front)
    section_view.getCameraNode().orientation.setValue(coin.SbRotation(*right.Q))
    G.updateGui()
    loop=QtCore.QEventLoop(); QtCore.QTimer.singleShot(1200,loop.quit); loop.exec_()
    section_view.fitAll()
    camera_node=section_view.getCameraNode()
    camera_node.height.setValue(camera_node.height.getValue()*1.25)
    G.updateGui()
    section_view.saveImage(str(folder/'section.png'),1000,1100,'White')
    A.closeDocument(section.Name)
    A.setActiveDocument(doc.Name)
    # Inside view of the actual OLED mount; no model or visibility is saved.
    for name in ('Shell','Controls','Hardware'):
        doc.getObject(name).Visibility=True
    for obj in doc.Objects:
        if hasattr(obj,'Shape'):obj.Visibility=False
    for name in ('FrontShell','Window','DisplayPCB','DisplayHeader','DisplayRetainer'):
        doc.getObject(name).Visibility=True
    oled_modes={name:doc.getObject(name).ViewObject.DisplayMode for name in ('FrontShell','DisplayPCB','DisplayHeader','DisplayRetainer')}
    for name in oled_modes:doc.getObject(name).ViewObject.DisplayMode='Flat Lines'
    oled_pose=A.Placement(A.Vector(0,18,165+18*27/38),
                         A.Rotation(A.Vector(0,1,0),A.Vector(0,27/38,-1)))
    inside=A.Rotation(A.Vector(0,1,0),180).multiply(A.Rotation(A.Vector(1,0,0),-90))
    save('oled-mount.png',oled_pose.Rotation.multiply(inside),
         oled_pose.Base,60)
    for name,mode in oled_modes.items():doc.getObject(name).ViewObject.DisplayMode=mode
    for name, state in visibility.items():
        doc.getObject(name).Visibility = state
    view.setCameraOrientation(camera)
    print('RENDER_OK')


target = os.environ.get('DISCORA_CAD_OUTPUT') or QtWidgets.QFileDialog.getExistingDirectory(
    None, '选择 Discora 模型目录生成预览')
if target:
    render(Path(target))
