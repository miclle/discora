"""Build the editable Discora V4 concept in FreeCAD. Units: mm."""
import math
import os
from pathlib import Path

import FreeCAD as A
import FreeCADGui as G
import Part
import Sketcher
from PySide import QtWidgets

V = A.Vector
X, Y, Z = V(1, 0, 0), V(0, 1, 0), V(0, 0, 1)
TEAL, BLACK, RUBBER = (0.025, 0.75, 0.72), (0.145, 0.155, 0.17), (0.07, 0.08, 0.09)
GLASS, PIXEL, DIM = (0.045, 0.085, 0.10), (0.48, 1.0, 0.97), (0.12, 0.18, 0.19)
WHITE, SILVER, PCB, BLUE = (0.94, 0.95, 0.94), (0.70, 0.73, 0.75), (0.14, 0.40, 0.32), (0.12, 0.33, 0.62)
# Concept dimensions. Drive depth is along X; its face is parallel to the XZ display.
WIDTH = 160.0
DRIVE = (129.0, 9.5, 128.0)
SPEAKER = (16.0, 24.0, 84.0)
BATTERY = (82.0, 21.0, 22.0)
SLOT_Y, SLOT_Z = 16.0, 86.0


def build(folder):
    doc = A.newDocument("DiscoraV4")
    doc.Label = "Discora V4 · 竖装 CD 播放器"
    visible = []

    def group(name, label):
        obj = doc.addObject("App::DocumentObjectGroup", name)
        obj.Label = label
        return obj

    shell = group("Shell", "01 · PLA 外壳")
    ui = group("Controls", "02 · 点阵屏和操控件")
    supports = group("Carrier", "03 · PLA 内部支架")
    hardware = group("Hardware", "04 · 硬件占位（待实测）")

    def finish(obj, name, color, parent):
        obj.Label = name
        parent.addObject(obj)
        obj.ViewObject.ShapeColor = color
        obj.ViewObject.DisplayMode = "Shaded"
        visible.append(obj)
        return obj

    def feature(key, label, shape, color, parent):
        obj = doc.addObject("Part::Feature", key)
        obj.Shape = shape
        return finish(obj, label, color, parent)

    def prism_yz(points, x, width):
        pts = [V(x, y, z) for y, z in points]
        return Part.Face(Part.makePolygon(pts + pts[:1])).extrude(X * width)

    def cylinder(radius, height, origin, axis):
        return Part.makeCylinder(radius, height, V(*origin), axis)

    def box(x, y, z, dx, dy, dz):
        return Part.makeBox(dx, dy, dz, V(x, y, z))

    def block(key, label, origin, dims, color, parent):
        obj = doc.addObject("Part::Box", key)
        obj.Length, obj.Width, obj.Height = dims
        obj.Placement = A.Placement(V(*origin), A.Rotation())
        return finish(obj, label, color, parent)

    def obround(origin, along, across, normal, length, width, thickness):
        c = V(*origin)
        r = width / 2
        a, b = c - along * (length / 2 - r), c + along * (length / 2 - r)
        edges = [Part.makeLine(a + across*r, b + across*r),
                 Part.Arc(b + across*r, b + along*r, b - across*r).toShape(),
                 Part.makeLine(b - across*r, a - across*r),
                 Part.Arc(a - across*r, a - along*r, a + across*r).toShape()]
        return Part.Face(Part.Wire(edges)).extrude(normal * thickness)

    def side_capsule(x, y, z, length, width, depth):
        return obround((x, y, z), Z, Y, X, length, width, depth)

    def native_cut(key, label, base, tool, color, parent):
        cutter = doc.addObject("Part::Feature", key + "Tool")
        cutter.Shape = tool
        cutter.Label = label + " · 刀体"
        obj = doc.addObject("Part::Cut", key)
        obj.Base, obj.Tool = base, cutter
        base.Visibility = cutter.Visibility = False
        return finish(obj, label, color, parent)

    def raw(key, shape):
        obj = doc.addObject("Part::Feature", key)
        obj.Shape = shape
        return obj

    # An editable sketch drives the continuous front, roof and handle extrusion.
    profile = [(0,3),(0,163),(38,190),(38,236),(43,236),(43,190),(78,165),
               (75,163.5),(41.5,187),(39,187),(3,161.5),(3,3)]
    section = doc.addObject("Sketcher::SketchObject", "FoldSection")
    section.Label = "壳体 YZ 截面 · 可编辑"
    section.Placement = A.Placement(V(-WIDTH/2,0,0), A.Rotation(V(1,1,1),120))
    for a,b in zip(profile, profile[1:] + profile[:1]):
        section.addGeometry(Part.LineSegment(V(*a,0),V(*b,0)),False)
    skin = doc.addObject("Part::Extrusion","FoldedSkin")
    skin.Base, skin.Dir, skin.Solid = section, X*WIDTH, True
    section.Visibility = False
    # Round top outer corners on the flange; preserve the crisp shoulder folds.
    doc.recompute()
    rounded = []
    for i, edge in enumerate(skin.Shape.Edges, 1):
        c = edge.CenterOfMass
        at_end = abs(abs(c.x)-WIDTH/2) < .01
        if at_end and abs(c.z-236) < .01:
            rounded.append((i, 4.0, 4.0))
        elif at_end and abs(c.y) < .01 and edge.Length > 150:
            rounded.append((i, 1.6, 1.6))
    fil = doc.addObject("Part::Fillet","CowlEdges")
    fil.Base, fil.Edges = skin, rounded
    skin.Visibility = False
    skin = fil
    normal = V(0,-27,38)
    normal.normalize()
    def deck(x,y):
        return V(x,y,163+27*y/38)
    holes = [obround((0,36,213), X,Z,Y,104,29,10),
             cylinder(56,9,(0,-3,82),Y)]
    for x,y,r in [(-49,18,11.25),(48,18,4.4)]:
        holes.append(Part.makeCylinder(r,12,deck(x,y)-normal*7,normal))
    native_cut("Cowl","前壳 · 斜面及一体提手",skin,Part.makeCompound(holes),TEAL,shell)

    # Each dark side panel sits below the cowl; the right panel has the disc slit.
    panel_profile = [(3,3),(75,3),(75,163.5),(41.5,187),(39,187),(3,161.5)]
    for right in [False,True]:
        prefix, label = ("R","右") if right else ("L","左")
        x = WIDTH/2-3 if right else -WIDTH/2
        base = raw(prefix+"PanelBlank",prism_yz(panel_profile,x,3))
        holes = [side_capsule(x-1,48,85,91,29,5)]
        if right:
            holes.append(side_capsule(x-1,SLOT_Y,SLOT_Z,124,3.2,5))
        native_cut(prefix+"Panel",label+"侧壳",base,Part.makeCompound(holes),BLACK,shell)
        # Recessed bezel and a separate perforated PLA grille.
        ring = side_capsule(x,48,85,90.8,28.8,2.9).cut(side_capsule(x-1,48,85,84,22,5))
        feature(prefix+"Bezel",label+"侧 · 胶囊形压圈",ring,RUBBER,shell)
        gx = x+0.4 if right else x+1.4
        grille = side_capsule(gx,48,85,84,22,1.2)
        vents = []
        for row in range(-16,17):
            dz = row * 2.45
            for col in range(-4,5):
                dy = (col + .5*(row%2)) * 2.7
                if dy**2 + max(0,abs(dz)-31)**2 < 9.5**2:
                    vents.append(cylinder(.86,3,(gx-.5,48+dy,85+dz),X))
        feature(prefix+"Grille",label+"侧 · 透孔护网",grille.cut(Part.makeCompound(vents)),BLACK,shell)
        # Purchased racetrack driver is behind the removable grille.
        depth, width, height = SPEAKER
        sx = WIDTH/2-3-depth if right else -WIDTH/2+3
        sy, sz = 48-width/2, 85-height/2
        block(prefix+"Driver",label+"声道 · 长方形喇叭包络",(sx,sy,sz),SPEAKER,RUBBER,hardware)
        collar = box(sx-1,sy-2,sz-2,depth+2,width+4,height+4).cut(
            box(sx-2,sy-.2,sz-.2,depth+4,width+.4,height+.4))
        # Stop at the inner wall.
        collar = collar.common(box(-WIDTH/2+3,3,6,WIDTH-6,72,156))
        feature(prefix+"DriverFrame",label+"喇叭安装框",collar,TEAL,supports)

    # Rear cover mates to integral base rails with four screw pilots.
    rear = prism_yz([(75,3),(78,3),(78,165),(75,163.5)],-80,160)
    tray = box(-77,3,3,154,72,3)
    for x in [-70,70]:
        upright = box(x-4,68,6,8,7,152)
        for z in [14,150]:
            rear = rear.cut(cylinder(1.7,5,(x,74,z),Y))
            upright = upright.cut(cylinder(1.25,6,(x,69.4,z),Y))
        tray = tray.fuse(upright)
    feature("Back","后盖 · 四个通孔",rear,BLACK,shell)
    feature("Base","底架 · 后盖螺钉柱",tray.removeSplitter(),BLACK,shell)
    feet = [cylinder(4,3,(x,y,0),Z) for x in [-61,61] for y in [11,67]]
    feature("Feet","四个脚垫",Part.makeCompound(feet),RUBBER,ui)

    feature("Window","点阵屏 · 圆形显示面",cylinder(55.8,2.3,(0,0.35,82),Y),GLASS,ui)
    emit, unlit = [], []
    for i in range(-19,20):
        for j in range(-19,20):
            u,v = 2.75*i,2.75*j
            radius = math.hypot(u,v)
            if radius>53: continue
            angle = math.degrees(math.atan2(v,u)) % 360
            mark = ((19<radius<47 and 6<angle<165 and (int(radius/4)%2==0))
                    or abs(radius-8)<1.2 or (8<=i<=14 and i%2==0 and -7<=j<-7+(i-6)))
            (emit if mark else unlit).append(cylinder(.76,.16,(u,.19,82+v),Y))
    feature("PixelField","点阵 · 暗像素示意",Part.makeCompound(unlit),DIM,ui)
    feature("PixelArt","点阵 · 曲线与音量图案示意",Part.makeCompound(emit),PIXEL,ui)
    feature("Keycap","播放键",Part.makeCylinder(11,1.45,deck(-49,18)-normal*.5,normal),TEAL,ui)
    key_mark=Part.makeBox(1.1,5,.15,V(-.55,-2.5,0))
    key_mark.Placement=A.Placement(deck(-49,18)+normal*.95,A.Rotation(Z,normal)).multiply(key_mark.Placement)
    feature("KeyLight","播放键 · 指示灯",key_mark,WHITE,ui)
    loc = deck(48,18)
    knob = Part.makeCylinder(11.8,8.2,loc+normal*.45,normal).cut(
        Part.makeCylinder(5.8,5.3,loc+normal*3.55,normal))
    feature("Knob","音量旋钮 · 内凹",knob,WHITE,ui)
    feature("Encoder","编码器包络",Part.makeCylinder(4,5,loc-normal*4.55,normal),SILVER,hardware)

    # Envelope has a real through-mouth so the swept CD volume can be checked.
    dw,dt,dh = DRIVE
    drive_x,drive_z=74-dw,SLOT_Z-dh/2
    drive = block("DriveBlank","光驱毛坯",(drive_x,SLOT_Y-dt/2,drive_z),DRIVE,SILVER,hardware)
    hardware.removeObject(drive)
    visible.remove(drive)
    native_cut("Drive","UJ-898 · 竖装估算包络",drive,
               box(drive_x+2,SLOT_Y-1,SLOT_Z-61,dw,2,122),SILVER,hardware)
    block("Bridge","SATA–USB 桥接包络",(drive_x-18,11,48),(18,10,29),PCB,hardware)
    # U-section channel supports the bottom edge and keeps the right opening free.
    guide_y = SLOT_Y-dt/2-2.15
    guide_width = dt+4.3
    channel = box(drive_x-1,guide_y,6,dw+1,guide_width,drive_z+3-6).cut(
        box(drive_x-2,guide_y+1.75,drive_z,dw+4,dt+.8,10))
    feature("DriveRail","光驱底部 U 形托轨",channel,TEAL,supports)
    rail = box(drive_x-1,guide_y,drive_z+dh-2,dw-1,guide_width,5).cut(
        box(drive_x-2,guide_y+1.75,drive_z+dh-3,dw+1,dt+.8,3.35))
    # The rear rib ties the upper and lower guides without crossing the disc path.
    spine = box(drive_x,guide_y+guide_width-1.2,drive_z+3,5,1.2,dh-5)
    feature("TopRail","光驱上定位条和后筋",rail.fuse(spine).removeSplitter(),TEAL,supports)

    sled = box(-53,65,42,106,2.4,98)
    for x in (-52,48):
        sled = sled.fuse(box(x,63,6,4,4.4,36))
    feature("ElectronicsSled","板卡背板及底脚",sled.removeSplitter(),TEAL,supports)
    for key,label,x,z,w,h in [
        ("MCU","ESP32-S3 N16R8",-49,57,27.94,63.39),
        ("DAC","立体声 DAC",-15,81,26,47),("Amp","立体声功放",18,59,32,54)]:
        block(key,label+" · 占位",(x,62.4,z),(w,1.6,h),PCB,hardware)
        block(key+"Chip",label+" · 元件高度示意",(x+3,57.4,z+6),(w-6,5,h*.47),
              SILVER if key=="MCU" else RUBBER,hardware)
        posts = [cylinder(2,1,(xx,64,zz),Y) for xx in (x+3,x+w-3) for zz in (z+3,z+h-3)]
        feature(key+"Pads",label+" · 支撑垫示意",Part.makeCompound(posts),TEAL,supports)
    bx, by, _ = BATTERY
    block("Battery","可充电电池包 · 占位",(-bx/2,38,8.5),BATTERY,BLUE,hardware)
    cradle = box(-bx/2-2,36,6,bx+4,by+4,13).cut(box(-bx/2-.3,37.7,8.5,bx+.6,by+.6,20))
    feature("BatteryCradle","底部电池座",cradle,TEAL,supports)

    doc.recompute()
    for o in visible:
        o.Visibility = True
        if o.Shape.isNull() or not o.Shape.isValid() or not o.Shape.Solids:
            raise RuntimeError("Invalid solid: " + o.Name)
    G.activeDocument().activeView().setCameraOrientation(A.Rotation(Z,21).multiply(
        A.Rotation(X,76)).Q)
    G.activeDocument().activeView().fitAll()
    doc.recompute()
    doc.saveAs(str(folder/"Discora-V4.FCStd"))
    return doc, visible


target = os.environ.get("DISCORA_CAD_OUTPUT") or QtWidgets.QFileDialog.getExistingDirectory(
    None, "选择 Discora 模型输出目录")
if target:
    build(Path(target))
